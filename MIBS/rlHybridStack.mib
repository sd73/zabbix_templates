CISCO-HYBRID-STACK-MIB DEFINITIONS ::= BEGIN

-- Title:               CISCO CISCO ROS
--                      This Private MIB supports the unit id configuration for hybrid stack of ROS products
-- Version:             7.50
-- Date:                21 mar 2011
-- 23-May-2012          Update unit id from 4 to 8 units maximum
-- 19-Dec-2012          Support Lion Native and advanced-hybrid-xg
-- 20-Jun-2013          Support stack ports list for SG500XG Native and advanced-hybrid-xg
-- 20-Jun-2013          Support s1s2_xg1xg2_xg stack ports pair for SG500X Native and advanced-hybrid-xg
-- 20-Jun-2013          Add MIB version for backwards/forwards compatability
-- 20-Jun-2013          Update MIB due to above changes
-- 11-Jul-2013          Add module type
-- 14-Jul-2013          More MIB changes



IMPORTS
    MacAddress                      FROM BRIDGE-MIB
    rnd                             FROM RADLAN-MIB
    OBJECT-TYPE,
    MODULE-IDENTITY                 FROM SNMPv2-SMI
    PortList                        FROM Q-BRIDGE-MIB
    TruthValue, TEXTUAL-CONVENTION  FROM SNMPv2-TC
    rlStack                         FROM RADLAN-STACK-MIB  ;

--rlStack MODULE-IDENTITY
--         LAST-UPDATED "200504140000Z"
--         ORGANIZATION "Marvell Semiconductor, Inc."
--         CONTACT-INFO
--				"5488 Marvell Lane
--				Santa Clara, CA 95054
--				USA
--	
--				Website:  www.marvell.com"
--         DESCRIPTION
--                "The private MIB module definition for stack."
--         REVISION "200504140000Z"
--        DESCRIPTION
--                "Initial revision."
--        ::= { rnd 107 }



StackMode ::= INTEGER {
   standalone           (1),
   native               (2),
   basic-hybrid         (3),
   advanced-hybrid      (4),
   advanced-hybrid-XG   (5)
}

PortsPair   ::= INTEGER {
   pair-s1s2            (1),
   pair-s3s4            (2),
   pair-s1s25G          (3),
   pair-s1s2Xg          (4),
   pair-lionXg          (5),
   pair-s1s2-xg1xg2-Xg  (6)
}

HybridStackPortSpeed  ::= INTEGER {
   port-speed-1G      (1),
   port-speed-5G      (2),
   port-speed-10G     (3),
   port-speed-auto    (4),
   port-speed-down    (5)
}

HybridStackDeviceMode  ::= INTEGER {
   mode-L2      (1),
   mode-L3      (2)
}

UnitModuleType ::= INTEGER {
   unit-Sx500      (1),
   unit-SG500X     (2),
   unit-SG500XG    (3)
}


rlStackHybridTable OBJECT-TYPE
    SYNTAX SEQUENCE OF RlStackHybridEntry
    MAX-ACCESS not-accessible
    STATUS     current
    DESCRIPTION
        " The table listing information required for hybrid stack."
    ::= {rlStack 5 }

rlStackHybridEntry  OBJECT-TYPE
    SYNTAX      RlStackHybridEntry
    MAX-ACCESS  not-accessible
    STATUS      current
    DESCRIPTION
        " An entry in the rlStackActiveUnitIdTable."
    INDEX {rlStackHybridUnitId }
    ::= {rlStackHybridTable  1 }


RlStackHybridEntry ::= SEQUENCE {
    rlStackHybridUnitId                             INTEGER,
    rlStackHybridStackMode                          StackMode,
    rlStackHybridPortsPair                          PortsPair,
    rlStackHybridPortNo1speedDeprecated             HybridStackPortSpeed,
    rlStackHybridPortNo2speedDeprecated             HybridStackPortSpeed,
    rlStackHybridUnitIdAfterReset                   INTEGER,
    rlStackHybridStackModeAfterReset                StackMode,
    rlStackHybridPortsPairAfterReset                PortsPair,
    rlStackHybridPortNo1speedAfterResetDeprecated   HybridStackPortSpeed,
    rlStackHybridPortNo2speedAfterResetDeprecated   HybridStackPortSpeed,
    rlStackHybridDeleteStartupAfterResetDeprecated  TruthValue,
    rlStackHybridDeviceModeAfterReset               HybridStackDeviceMode,
    rlStackHybridXgPortNo1NumDeprecated             INTEGER,
    rlStackHybridXgPortNo1NumAfterResetDeprecated   INTEGER,
    rlStackHybridXgPortNo2NumDeprecated             INTEGER,
    rlStackHybridXgPortNo2NumAfterResetDeprecated   INTEGER,
    rlStackHybridPortSpeed                          HybridStackPortSpeed,
    rlStackHybridPortSpeedAfterReset                HybridStackPortSpeed,
    rlStackHybridXgPortList                         OCTET STRING,
    rlStackHybridXgPortListAfterReset               OCTET STRING,
    rlStackHybridMibVersion                         INTEGER,
    rlStackHybridUnitModuleType                     UnitModuleType
}

rlStackHybridUnitId OBJECT-TYPE
    SYNTAX      INTEGER (1..8)
    MAX-ACCESS  not-accessible
    STATUS      current
    DESCRIPTION
        "The unit number device, which is the active unit id"
    ::= {rlStackHybridEntry 1 }


rlStackHybridStackMode OBJECT-TYPE
    SYNTAX      StackMode
    MAX-ACCESS  read-only
    STATUS      current
    DESCRIPTION
        "Indicates the unit stack mode."
    ::= {rlStackHybridEntry 2 }


rlStackHybridPortsPair OBJECT-TYPE
    SYNTAX      PortsPair
    MAX-ACCESS  read-only
    STATUS      current
    DESCRIPTION
        "Indicates the stack ports pair."
    ::= {rlStackHybridEntry 3 }


rlStackHybridPortNo1speedDeprecated OBJECT-TYPE
    SYNTAX      HybridStackPortSpeed
    MAX-ACCESS  read-only
    STATUS      current
    DESCRIPTION
        "Indicates the first stack port speed."
    ::= {rlStackHybridEntry 4 }

rlStackHybridPortNo2speedDeprecated OBJECT-TYPE
    SYNTAX      HybridStackPortSpeed
    MAX-ACCESS  read-only
    STATUS      current
    DESCRIPTION
        "Indicates the second stack port speed."
    ::= {rlStackHybridEntry 5 }

rlStackHybridUnitIdAfterReset OBJECT-TYPE
    SYNTAX      INTEGER (0..8)
    MAX-ACCESS  read-write
    STATUS      current
    DESCRIPTION
        "Indicates the unit id that will be after reset."
    ::= {rlStackHybridEntry 6 }


rlStackHybridStackModeAfterReset OBJECT-TYPE
    SYNTAX      StackMode
    MAX-ACCESS  read-write
    STATUS      current
    DESCRIPTION
        "Indicates the unit stack mode that will be after reset."
    ::= {rlStackHybridEntry 7 }

rlStackHybridPortsPairAfterReset OBJECT-TYPE
    SYNTAX      PortsPair
    MAX-ACCESS  read-write
    STATUS      current
    DESCRIPTION
        "Indicates the stack ports pair that will be after reset."
    ::= {rlStackHybridEntry 8 }

rlStackHybridPortNo1speedAfterResetDeprecated OBJECT-TYPE
    SYNTAX      HybridStackPortSpeed
    MAX-ACCESS  read-write
    STATUS      current
    DESCRIPTION
        "Indicates the first stack port speed that will be after reset."
    ::= {rlStackHybridEntry 9 }

rlStackHybridPortNo2speedAfterResetDeprecated OBJECT-TYPE
    SYNTAX      HybridStackPortSpeed
    MAX-ACCESS  read-write
    STATUS      current
    DESCRIPTION
        "Indicates the second stack port speed that will be after reset."
    ::= {rlStackHybridEntry 10 }

rlStackHybridDeleteStartupAfterResetDeprecated OBJECT-TYPE
    SYNTAX      TruthValue
    MAX-ACCESS  read-only
    STATUS      current
    DESCRIPTION
        "Indicates whether the startup configuration is deleted after reset."
    ::= {rlStackHybridEntry 11 }
    
rlStackHybridDeviceModeAfterReset OBJECT-TYPE
    SYNTAX      HybridStackDeviceMode
    MAX-ACCESS  read-only
    STATUS      current
    DESCRIPTION
        "Indicates Device mode (Layer2 or Layer3) after reset."
    ::= {rlStackHybridEntry 12 }

rlStackHybridXgPortNo1NumDeprecated OBJECT-TYPE
    SYNTAX      INTEGER
    MAX-ACCESS  read-only
    STATUS      current
    DESCRIPTION
        "Indicates the first XG stack port number."
    ::= {rlStackHybridEntry 13 }

rlStackHybridXgPortNo1NumAfterResetDeprecated OBJECT-TYPE
    SYNTAX      INTEGER
    MAX-ACCESS  read-write
    STATUS      current
    DESCRIPTION
        "Indicates the first XG stack port number that will be after reset."
    ::= {rlStackHybridEntry 14 }

rlStackHybridXgPortNo2NumDeprecated OBJECT-TYPE
    SYNTAX      INTEGER
    MAX-ACCESS  read-only
    STATUS      current
    DESCRIPTION
        "Indicates the second XG stack port number."
    ::= {rlStackHybridEntry 15 }

rlStackHybridXgPortNo2NumAfterResetDeprecated OBJECT-TYPE
    SYNTAX      INTEGER
    MAX-ACCESS  read-write
    STATUS      current
    DESCRIPTION
        "Indicates the second XG stack port number that will be after reset."
    ::= {rlStackHybridEntry 16 }

rlStackHybridPortSpeed OBJECT-TYPE
    SYNTAX      HybridStackPortSpeed
    MAX-ACCESS  read-only
    STATUS      current
    DESCRIPTION
        "Indicates the stack ports pair speed."
    ::= {rlStackHybridEntry 17 }

rlStackHybridPortSpeedAfterReset OBJECT-TYPE
    SYNTAX      HybridStackPortSpeed
    MAX-ACCESS  read-write
    STATUS      current
    DESCRIPTION
        "Indicates the stack ports pair speed that will be after reset."
    ::= {rlStackHybridEntry 18 }

rlStackHybridXgPortList OBJECT-TYPE
    SYNTAX      OCTET STRING (SIZE (2..16))
    MAX-ACCESS  read-only
    STATUS      current
    DESCRIPTION
        "Indicates the XG stack ports list.
        A set of ports that are identified by a PortList, in which
        each port is represented as a bit."
    ::= {rlStackHybridEntry 19 }

rlStackHybridXgPortListAfterReset OBJECT-TYPE
    SYNTAX      OCTET STRING (SIZE (2..16))
    MAX-ACCESS  read-write
    STATUS      current
    DESCRIPTION
        "Indicates the XG stack ports list that will be after reset.
        A set of ports that are identified by a PortList, in which
        each port is represented as a bit."
    ::= {rlStackHybridEntry 20 }

rlStackHybridUnitModuleType OBJECT-TYPE
    SYNTAX      UnitModuleType
    MAX-ACCESS  read-only
    STATUS      current
    DESCRIPTION
        "Indicates the stack unit module."
    ::= {rlStackHybridEntry 21 }

rlStackHybridMibVersion OBJECT-TYPE
    SYNTAX      INTEGER
    MAX-ACCESS  read-write
    STATUS      current
    DESCRIPTION
        "Indicates the Hybrid Stack MIB version"
    ::= {rlStackHybridEntry 22 }


--rlStackHybridConvertSPortsPairToIfIndexTable OBJECT-TYPE
--    SYNTAX SEQUENCE OF RlStackHybridConvertSPortsPairToIfIndexEntry
--    MAX-ACCESS not-accessible
--    STATUS     current
--    DESCRIPTION
--        " The table listing information required to convert hybrid stack ports pair up to 4 ifIndexes."
--    ::= {rlStack 6 }
--
--rlStackHybridConvertSPortsPairToIfIndexEntry  OBJECT-TYPE
--    SYNTAX      RlStackHybridConvertSPortsPairToIfIndexEntry
--    MAX-ACCESS  not-accessible
--    STATUS      current
--    DESCRIPTION
--        " An entry in the rlStackHybridConvertSPortsPairToIfIndexTable."
--    INDEX {rlStackHybridPortsPair }
--    ::= {rlStackHybridConvertSPortsPairToIfIndexTable  1 }
--
--RlStackHybridConvertSPortsPairToIfIndexEntry ::= SEQUENCE {
--    rlStackHybridConvertSPortsPair                      PortsPair,
--    rlCascadeIfIndexPort1                               INTEGER,
--    rlCascadeIfIndexPort2                               INTEGER,
--    rlCascadeIfIndexPort3                               INTEGER,
--    rlCascadeIfIndexPort4                               INTEGER
--}
--
--rlStackHybridConvertSPortsPair OBJECT-TYPE
--    SYNTAX      PortsPair
--    MAX-ACCESS  not-accessible
--    STATUS      current
--    DESCRIPTION
--        "Indicates the PortsPair."
--    ::= {rlStackHybridConvertSPortsPairToIfIndexEntry 1 }
--
--rlCascadeIfIndexPort1 OBJECT-TYPE
--    SYNTAX InterfaceIndex
--    MAX-ACCESS read-only
--    STATUS current
--    DESCRIPTION
--        "The port's 1st interface index."
--    ::= { rlStackHybridConvertSPortsPairToIfIndexEntry 2 }
--
--rlCascadeIfIndexPort2 OBJECT-TYPE
--    SYNTAX InterfaceIndex
--    MAX-ACCESS read-only
--    STATUS current
--    DESCRIPTION
--        "The port's 2nd interface index."
--    ::= { rlStackHybridConvertSPortsPairToIfIndexEntry 3 }
--
--rlCascadeIfIndexPort3 OBJECT-TYPE
--    SYNTAX InterfaceIndex
--    MAX-ACCESS read-only
--    STATUS current
--    DESCRIPTION
--        "The port's 3rd interface index."
--    ::= { rlStackHybridConvertSPortsPairToIfIndexEntry 4 }
--
--rlCascadeIfIndexPort4 OBJECT-TYPE
--    SYNTAX InterfaceIndex
--    MAX-ACCESS read-only
--    STATUS current
--    DESCRIPTION
--        "The port's 4th interface index."
--    ::= { rlStackHybridConvertSPortsPairToIfIndexEntry 5 }


END
