RADLAN-BGP DEFINITIONS ::= BEGIN

-- Title:      RADLAN BGP4 Private Extension
-- Version:    7.37.00.00
-- Date:       17 May 2004

IMPORTS
    rnd                                                     FROM RADLAN-MIB
    bgpPeerEntry , bgpPeerRemoteAddr, bgp4PathAttrEntry,
    bgp4PathAttrIpAddrPrefix, bgp4PathAttrIpAddrPrefixLen,
    bgp4PathAttrPeer                                        FROM BGP4-MIB
    Unsigned32, Integer32, Counter32, IpAddress,
    MODULE-IDENTITY, OBJECT-TYPE                            FROM SNMPv2-SMI
    DisplayString,
    RowStatus, TruthValue, TEXTUAL-CONVENTION               FROM SNMPv2-TC;

rlBgp            MODULE-IDENTITY
                 LAST-UPDATED "200406010000Z"
                 ORGANIZATION "Marvell Semiconductor, Inc."
                 CONTACT-INFO
					"5488 Marvell Lane
					Santa Clara, CA 95054
					USA

					Website:  www.marvell.com"
                 DESCRIPTION
                      "The private MIB module definition for RND BGP private MIB."
                 REVISION "200406010000Z"
                 DESCRIPTION
                      "Initial version of this MIB."
                 ::= { rnd 71 }


 rlBgpMibVersion OBJECT-TYPE
    SYNTAX      INTEGER
    MAX-ACCESS  read-only
    STATUS      current
    DESCRIPTION
        "BGP4 Mib version, the current version is 1."
    ::= { rlBgp 1 }

 rlBgpPeersExtTable OBJECT-TYPE
     SYNTAX     SEQUENCE OF RlBgpPeersExtEntry
     MAX-ACCESS not-accessible
     STATUS     current
     DESCRIPTION
         "BGP peer table. Contains one entry per BGP peer,
          information about the connections with BGP peers."
     ::= { rlBgp 2 }

 rlBgpPeersExtEntry OBJECT-TYPE
     SYNTAX     RlBgpPeersExtEntry
     MAX-ACCESS not-accessible
     STATUS     current
     DESCRIPTION
         "Entry containing information about the connection with
          a BGP peer. "
     AUGMENTS    { bgpPeerEntry }
     ::= { rlBgpPeersExtTable 1 }

 RlBgpPeersExtEntry ::= SEQUENCE {
     rlBgpPeersExtRowStatus             RowStatus,
     rlBgpPeersExtIsReflectorClient     INTEGER,
     rlBgpPeersExtInConfederation       TruthValue,
     rlBgpPeersExtRemAS                 INTEGER
 }

 rlBgpPeersExtRowStatus OBJECT-TYPE
     SYNTAX     RowStatus
     MAX-ACCESS read-write
     STATUS     current
     DESCRIPTION
         "The row status variable, used according to installation
         and removal conventions for conceptual rows. Setting this
         object to active(1) or createAndGo(4) results in the
         addition of the remote address of the peer.
         Destroying the entry or setting it to notInService(2)
         removes the remote address associated with the peer.
         The use of other values is implementation-dependent."
     DEFVAL { active }
 ::= { rlBgpPeersExtEntry 1 }

 rlBgpPeersExtIsReflectorClient OBJECT-TYPE
     SYNTAX   INTEGER {
        nonClient(0),
        client(1),
        meshedClient(2)
     }
     MAX-ACCESS read-write
        STATUS  current
     DESCRIPTION
         "This value indicates whether the given peer is a
          reflector client of this router, or not.
          A value of client indicates that this peer is a
          reflector client that is not fully meshed with
          other reflector clients. A value of meshedClient
          indicates that the peer is a reflector client and
          is fully meshed with all other clients because
          there is no route reflection. The default value
          is meshedClient."
     DEFVAL { meshedClient }
 ::= { rlBgpPeersExtEntry 2 }

 rlBgpPeersExtInConfederation OBJECT-TYPE
     SYNTAX      TruthValue
     MAX-ACCESS  read-write
     STATUS      current
     DESCRIPTION
          "This value indicates whether the given peer is in
          our confederation or not."
     DEFVAL { false }
 ::= { rlBgpPeersExtEntry 3 }

 rlBgpPeersExtRemAS OBJECT-TYPE
     SYNTAX     INTEGER (0..65535)
     MAX-ACCESS read-write
     STATUS     current
     DESCRIPTION
             "The remote autonomous system number which is configurable."
     DEFVAL { 0 }
 ::= { rlBgpPeersExtEntry 4 }

 rlBgpClusterId OBJECT-TYPE
     SYNTAX     IpAddress
     MAX-ACCESS read-write
     STATUS     current
     DESCRIPTION
          "The configured Cluster-ID of the local router. A
          value of 0.0.0.0 indicates the absence of this
          value."
 ::= { rlBgp 3 }

 rlBgpConfederationId OBJECT-TYPE
     SYNTAX     INTEGER (0..65535)
     MAX-ACCESS read-write
     STATUS     current
     DESCRIPTION
             "The local Confederation Identification
              Number. A value of zero (0) indicates the
              absence of this value."
 ::= { rlBgp 4 }

 rlBgpEnable   OBJECT-TYPE
      SYNTAX INTEGER {
        enable(1),
        disable(2)
      }
      MAX-ACCESS  read-write
      STATUS      current
      DESCRIPTION
        "This value indicates whether BGP is enable on
         this router or not."
   ::={ rlBgp 5 }

 rlBgpRouteReflectionEnable   OBJECT-TYPE
      SYNTAX    INTEGER {
        enable(1),
        disable(2)
      }
      MAX-ACCESS  read-write
      STATUS      current
      DESCRIPTION
        "This value indicates whether route reflection extension is enable on
         this router or not."
   ::={ rlBgp 6 }

 rlBgpASConfederationEnable   OBJECT-TYPE
      SYNTAX    INTEGER {
        enable(1),
        disable(2)
      }
      MAX-ACCESS read-write
      STATUS     current
      DESCRIPTION
        "This value indicates whether AS confederation extension is enable on
         this router or not."
   ::={ rlBgp 7 }

 rlBgpRouteFlapDampeningEnable   OBJECT-TYPE
      SYNTAX    INTEGER {
        enable(1),
        disable(2)
      }
      MAX-ACCESS  read-write
      STATUS      current
      DESCRIPTION
        "This value indicates whether route flap dampening extension is enable
         on this router or not."
   ::={ rlBgp 8 }

 rlBgpCommunitiesEnable   OBJECT-TYPE
      SYNTAX    INTEGER {
        enable(1),
        disable(2)
      }
      MAX-ACCESS  read-write
      STATUS      current
      DESCRIPTION
        "This value indicates whether BGP communities extension is enable on
         this router or not."
   ::={ rlBgp 9 }

 rlBgpCapabilNegotEnable   OBJECT-TYPE
      SYNTAX    INTEGER {
        enable(1),
        disable(2)
      }
      MAX-ACCESS  read-write
      STATUS      current
      DESCRIPTION
        "This value indicates whether BGP capabilities negotiation extension
         is enable on this router or not."
   ::={ rlBgp 10 }

  rlBgpMedConf OBJECT-TYPE
      SYNTAX            INTEGER (-1..2147483647)
      MAX-ACCESS        read-write
      STATUS            current
      DESCRIPTION
           "The configured Multi-Exit Descriminator of the local router.
            A value of -1 indicates the absence of this attribute."
  ::= { rlBgp 11 }

  rlBgpLocalPrefConf OBJECT-TYPE
      SYNTAX            INTEGER (-1..2147483647)
      MAX-ACCESS        read-write
      STATUS            current
      DESCRIPTION
           "The configured Local Preference of the local router.
            A value of -1 indicates the absence of this attribute."
  ::= { rlBgp 12 }

 rlBgpLocalAsConf OBJECT-TYPE
      SYNTAX         INTEGER (0..65535)
      MAX-ACCESS     read-write
      STATUS         current
      DESCRIPTION
              "The local autonomous system number, which is
               configurable."
 ::= { rlBgp 13 }

 rlBgp4PathAttrExtTable OBJECT-TYPE
     SYNTAX             SEQUENCE OF RlBgp4PathAttrExtEntry
     MAX-ACCESS         not-accessible
     STATUS             current
     DESCRIPTION
         "The BGP-4 Received Path Attribute Table contains
          information about paths to destination networks
          received from all BGP4 peers."
     ::= { rlBgp 14 }

 rlBgp4PathAttrExtEntry OBJECT-TYPE
     SYNTAX             RlBgp4PathAttrExtEntry
     MAX-ACCESS         not-accessible
     STATUS             current
     DESCRIPTION
         "Information about a path to a network."
     AUGMENTS    { bgp4PathAttrEntry }
     ::= { rlBgp4PathAttrExtTable 1 }

 RlBgp4PathAttrExtEntry ::= SEQUENCE {
         rlBgp4PathAttrOriginatorId     IpAddress,
         rlBgp4PathAttrClusterList      OCTET STRING,
         rlBgp4PathAttrCommunities      OCTET STRING
     }

 rlBgp4PathAttrOriginatorId OBJECT-TYPE
            SYNTAX              IpAddress
            MAX-ACCESS          read-only
            STATUS              current
            DESCRIPTION
                    "The Originator-ID identifying the router that initially
                     advertised this destination to a Route Reflector.  A
                     value of 0.0.0.0 indicates the absence of this attribute.
                     This attribute is defined in [RFC2796]."
            ::= { rlBgp4PathAttrExtEntry 1 }

 rlBgp4PathAttrClusterList OBJECT-TYPE
            SYNTAX              OCTET STRING (SIZE(0..4096))
            MAX-ACCESS          read-only
            STATUS              current
            DESCRIPTION
                    "A sequence of four octet long values representing the
                     reflection path that the route has passed.  Each four
                     octet long value represents the ID of a cluster that
                     the route has traversed.  A length of zero (0) indicates
                     the absence of this attribute.  This attribute is defined
                     in [RFC2796]."
            ::= { rlBgp4PathAttrExtEntry 2 }

 rlBgp4PathAttrCommunities OBJECT-TYPE
            SYNTAX              OCTET STRING (SIZE(0..4096))
            MAX-ACCESS          read-only
            STATUS              current
            DESCRIPTION
                    "A sequence of four octet long values representing the
                     community that was received with the route.  The values
                     of each of the individual octets may have semantic meaning.
                     A length of zero (0) indicates the absence of this attribute.
                     This attribute is defined in [RFC1997]."
            ::= { rlBgp4PathAttrExtEntry 3 }

  rlBgpSuppressLimit OBJECT-TYPE
      SYNTAX            INTEGER (1..20000)
      MAX-ACCESS        read-write
      STATUS            current
      DESCRIPTION
              "A numeric value that is compared with the penalty. If the penalty
               is greater than the suppress limit, the route is suppressed.
               Default value is 2000."
 ::= { rlBgp 15 }

  rlBgpReuseLimit OBJECT-TYPE
      SYNTAX            INTEGER (1..20000)
      MAX-ACCESS        read-write
      STATUS            current
      DESCRIPTION
              "A configurable numeric value that is compared with the penalty.
               If the penalty is less than the reuse limit, a suppressed route
               that is up will no longer be suppressed. Default value is 750."
 ::= { rlBgp 16 }

 rlBgpHalfLifeTime OBJECT-TYPE
      SYNTAX        INTEGER (1..45)
      MAX-ACCESS    read-write
      STATUS        current
      DESCRIPTION
              "A configurable numeric value that describes the time required to
               reduce the penalty by one half. Default value is 15."
 ::= { rlBgp 17 }

  rlBgpMaxSuppressTime OBJECT-TYPE
      SYNTAX     INTEGER (1..255)
      MAX-ACCESS read-write
      STATUS     current
      DESCRIPTION
              "A configurable numeric value that describes the maximum time a
               route can be suppressed no matter how unstable it has been prior
               to this period ofstability. Default value is 4*rlBgpHalfLifeTime."
 ::= { rlBgp 18 }

END
