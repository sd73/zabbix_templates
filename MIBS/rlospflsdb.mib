RADLAN-OSPF-LSDB-MIB DEFINITIONS ::= BEGIN

-- Title:                RADLAN OSPF LSDB
--                       OSPF LSA Database Private MIB
-- Version:              0.00
-- Date:                 17 Feb 2012

IMPORTS
    MODULE-IDENTITY, OBJECT-TYPE, Counter32, Gauge32,
        Integer32, Unsigned32, IpAddress
        FROM SNMPv2-SMI
    TEXTUAL-CONVENTION, TruthValue, RowStatus, TimeStamp
        FROM SNMPv2-TC
    rlOspf
        FROM RADLAN-OSPF-MIB
    RlOspfProcessID, rlOspfIfEntry, rlOspfVirtIfEntry
        FROM RADLAN-OSPF-MIB
    AreaID, RouterID
        FROM OSPF-MIB
    rnd                                      FROM RADLAN-MIB
    mib-2                                    FROM RFC1213-MIB;


rlOspfLsdb MODULE-IDENTITY
        LAST-UPDATED "201105041700Z" -- Wed Feb 17 17:00:00 PST 2012
        ORGANIZATION "Marvell Semiconductor, Inc."
        CONTACT-INFO
			"5488 Marvell Lane
			Santa Clara, CA 95054
			USA

			Website:  www.marvell.com"
        DESCRIPTION
             "The private MIB module definition for OSPF LSA Database MIB."
        REVISION "201105041700Z"
        DESCRIPTION
             "Initial version of this MIB."
    ::= { rnd 221 }

------------------------------------------------------------------------------
--  OSPF Link State Database
------------------------------------------------------------------------------


------------------------------------------------------------------------------
--  OSPF Router LSA Table
------------------------------------------------------------------------------

rlOspfRouterLsaTable OBJECT-TYPE
    SYNTAX      SEQUENCE OF RlOspfRouterLsaEntry
    MAX-ACCESS  not-accessible
    STATUS      current
    DESCRIPTION
        "Router Link State Advertisement."
    ::= { rlOspfLsdb 1 }


rlOspfRouterLsaEntry OBJECT-TYPE
    SYNTAX      RlOspfRouterLsaEntry
    MAX-ACCESS  not-accessible
    STATUS      current
    DESCRIPTION
    "A single entry from Router LSA."
    INDEX { rlOspfRouterLsaProcessId, rlOspfRouterLsaAreaId, rlOspfRouterLsaLsid,
            rlOspfRouterLsaRouterId, rlOspfRouterLsaIdx }
       ::= { rlOspfRouterLsaTable 1 }

RlOspfRouterLsaEntry ::=
    SEQUENCE {
        rlOspfRouterLsaProcessId
            RlOspfProcessID,
        rlOspfRouterLsaAreaId
            AreaID,
        rlOspfRouterLsaLsid
            IpAddress,
        rlOspfRouterLsaRouterId
            RouterID,
        rlOspfRouterLsaIdx
            Unsigned32,
        rlOspfRouterLsaSequence
            Integer32,
        rlOspfRouterLsaAge
            Integer32,
        rlOspfRouterLsaChecksum
            Integer32,
        rlOspfRouterLsaLength
            Unsigned32,
        rlOspfRouterLsaBitV
            INTEGER,
        rlOspfRouterLsaBitE
            INTEGER,
        rlOspfRouterLsaBitB
            INTEGER,
        rlOspfRouterLsaLinks
            Unsigned32,
        rlOspfRouterLsaLinkID
            IpAddress,
        rlOspfRouterLsaLinkData
            IpAddress,
        rlOspfRouterLsaType
            INTEGER,
        rlOspfRouterLsaMetric
            Unsigned32
}

rlOspfRouterLsaProcessId OBJECT-TYPE
      SYNTAX   RlOspfProcessID
      MAX-ACCESS   read-only
      STATUS   current
      DESCRIPTION
         "A 32-bit integer uniquely identifying an OSPF process."
    ::= { rlOspfRouterLsaEntry 1 }

rlOspfRouterLsaAreaId OBJECT-TYPE
    SYNTAX      AreaID
    MAX-ACCESS  read-only
    STATUS      current
    DESCRIPTION
       "The 32 bit identifier of the Area  from  which
        the LSA was received."
    REFERENCE
       "OSPF Version 2, Appendix C.2 Area parameters"
  ::= { rlOspfRouterLsaEntry 2 }

rlOspfRouterLsaLsid OBJECT-TYPE
    SYNTAX      IpAddress
    MAX-ACCESS  read-only
    STATUS      current
    DESCRIPTION
       "The Link State ID is an LS Type Specific field
        containing either a Router ID or an IP Address;
        it identifies the piece of the  routing  domain
        that is being described by the advertisement."
    REFERENCE
       "OSPF Version 2, Section 12.1.4 Link State ID"
  ::= { rlOspfRouterLsaEntry 3 }

rlOspfRouterLsaRouterId OBJECT-TYPE
    SYNTAX      RouterID
    MAX-ACCESS  read-only
    STATUS      current
    DESCRIPTION
       "The 32 bit number that uniquely identifies the
        originating router in the Autonomous System."
    REFERENCE
       "OSPF Version 2, Appendix C.1 Global parameters"
  ::= { rlOspfRouterLsaEntry 4 }

rlOspfRouterLsaIdx OBJECT-TYPE
    SYNTAX      Unsigned32 (1.. 65535)
    MAX-ACCESS  read-only
    STATUS      current
    DESCRIPTION
       "The index is a unsigned 32-bit integer.
        It is used as sequence number of entry
        in the LSA and relevant only for Router
        or Network LSA which can contain
        unlimited number of entries."
  ::= { rlOspfRouterLsaEntry 5 }

rlOspfRouterLsaSequence OBJECT-TYPE
    SYNTAX      Integer32
    MAX-ACCESS  read-only
    STATUS      current
    DESCRIPTION
       "The sequence number field is a signed  32-bit
        integer. It is used to detect old and duplicate
        link state advertisements. The space of sequence
        numbers is linearly ordered. The larger the
        sequence number the more recent the advertisement."
    REFERENCE
       "OSPF Version 2, Section 12.1.6 LS sequence number"
  ::= { rlOspfRouterLsaEntry 6 }


rlOspfRouterLsaAge OBJECT-TYPE
    SYNTAX      Integer32    -- Should be 0..MaxAge
    MAX-ACCESS  read-only
    STATUS      current
    DESCRIPTION
       "This field is the age of the link state
        advertisement in seconds."
       REFERENCE
          "OSPF Version 2, Section 12.1.1 LS age"
  ::= { rlOspfRouterLsaEntry 7 }

rlOspfRouterLsaChecksum OBJECT-TYPE
    SYNTAX      Integer32
    MAX-ACCESS  read-only
    STATUS      current
    DESCRIPTION
       "This field is the checksum of the complete contents
        of the advertisement, excepting the age field.
        The age field is excepted so that an advertisement's
        age can be incremented without updating the checksum.
        The checksum used is the same that is used for ISO
        connectionless datagrams; it is commonly referred
        to as the Fletcher checksum."
    REFERENCE
       "OSPF Version 2, Section 12.1.7 LS checksum"
  ::= { rlOspfRouterLsaEntry 8 }

rlOspfRouterLsaLength OBJECT-TYPE
    SYNTAX      Unsigned32
    MAX-ACCESS  read-only
    STATUS      current
    DESCRIPTION
       "The lenth in bytes of the LSA.
        This includes the 20 byte LSA header."
  ::= { rlOspfRouterLsaEntry 9 }

rlOspfRouterLsaBitV OBJECT-TYPE
    SYNTAX INTEGER {
        off(1),
        on(2)
    }
    MAX-ACCESS   read-only
    STATUS      current
    DESCRIPTION
       "When set, the router is an endpoint
        of one or more fully adjacent virtual
        links having the described area as Transit
        area (V is for virtual link endpoint)."
  ::= { rlOspfRouterLsaEntry 10 }

rlOspfRouterLsaBitE OBJECT-TYPE
    SYNTAX INTEGER {
        off(1),
        on(2)
    }
    MAX-ACCESS   read-only
        STATUS   current
    DESCRIPTION
       "When set, the router is an AS
        boundary router (E is for external)."
  ::= { rlOspfRouterLsaEntry 11 }

rlOspfRouterLsaBitB OBJECT-TYPE
    SYNTAX INTEGER {
        off(1),
        on(2)
    }
    MAX-ACCESS   read-only
    STATUS      current
    DESCRIPTION
       "When set, the router is an area
        border router (B is for border)."
  ::= { rlOspfRouterLsaEntry 12 }

rlOspfRouterLsaLinks OBJECT-TYPE
    SYNTAX      Unsigned32
    MAX-ACCESS  read-only
    STATUS      current
    DESCRIPTION
       "The number of router links described in this LSA.
        This must be the total collection of router links
        (i.e., interfaces) to the area."
  ::= { rlOspfRouterLsaEntry 13 }

rlOspfRouterLsaLinkID OBJECT-TYPE
    SYNTAX      IpAddress
    MAX-ACCESS  read-only
    STATUS      current
    DESCRIPTION
       "Identifies the object that this router link
        connects to. Value depends on the link's Type."
  ::= { rlOspfRouterLsaEntry 14 }

rlOspfRouterLsaLinkData OBJECT-TYPE
    SYNTAX      IpAddress
    MAX-ACCESS  read-only
    STATUS      current
    DESCRIPTION
       "Value depends on the link's Type field."
  ::= { rlOspfRouterLsaEntry 15 }

rlOspfRouterLsaType OBJECT-TYPE
    SYNTAX INTEGER {
        pointToPoint(1),
        transitNetwork(2),
        stubNetwork(3),
        virtualLink(4)
    }
    MAX-ACCESS   read-only
        STATUS   current
    DESCRIPTION
       "A quick description of the router link."
  ::= { rlOspfRouterLsaEntry 16 }

rlOspfRouterLsaMetric OBJECT-TYPE
    SYNTAX      Unsigned32
    MAX-ACCESS  read-only
    STATUS      current
    DESCRIPTION
       "The cost of using this router link."
  ::= { rlOspfRouterLsaEntry 17 }

------------------------------------------------------------------------------
--  OSPF Network LSA Table
------------------------------------------------------------------------------

rlOspfNetworkLsaTable OBJECT-TYPE
    SYNTAX      SEQUENCE OF RlOspfNetworkLsaEntry
    MAX-ACCESS  not-accessible
    STATUS      current
    DESCRIPTION
        "Network Link State Advertisement."
    ::= { rlOspfLsdb 2 }

rlOspfNetworkLsaEntry OBJECT-TYPE
    SYNTAX      RlOspfNetworkLsaEntry
    MAX-ACCESS  not-accessible
    STATUS      current
    DESCRIPTION
    "A single entry from Network LSA."
    INDEX { rlOspfNetworkLsaProcessId, rlOspfNetworkLsaAreaId, rlOspfNetworkLsaLsid,
            rlOspfNetworkLsaRouterId, rlOspfNetworkLsaIdx }
       ::= { rlOspfNetworkLsaTable 1 }

RlOspfNetworkLsaEntry ::=
    SEQUENCE {
        rlOspfNetworkLsaProcessId
            RlOspfProcessID,
        rlOspfNetworkLsaAreaId
            AreaID,
        rlOspfNetworkLsaLsid
            IpAddress,
        rlOspfNetworkLsaRouterId
            RouterID,
        rlOspfNetworkLsaIdx
            Unsigned32,
        rlOspfNetworkLsaSequence
            Integer32,
        rlOspfNetworkLsaAge
            Integer32,
        rlOspfNetworkLsaChecksum
            Integer32,
        rlOspfNetworkLsaLength
            Unsigned32,
        rlOspfNetworkLsaMask
            IpAddress,
        rlOspfNetworkLsaAttRouter
            IpAddress
}

rlOspfNetworkLsaProcessId OBJECT-TYPE
      SYNTAX   RlOspfProcessID
      MAX-ACCESS   read-only
      STATUS   current
      DESCRIPTION
         "A 32-bit integer uniquely identifying an OSPF process."
    ::= { rlOspfNetworkLsaEntry 1 }

rlOspfNetworkLsaAreaId OBJECT-TYPE
    SYNTAX      AreaID
    MAX-ACCESS  read-only
    STATUS      current
    DESCRIPTION
       "The 32 bit identifier of the Area  from  which
        the LSA was received."
    REFERENCE
       "OSPF Version 2, Appendix C.2 Area parameters"
  ::= { rlOspfNetworkLsaEntry 2 }

rlOspfNetworkLsaLsid OBJECT-TYPE
    SYNTAX      IpAddress
    MAX-ACCESS  read-only
    STATUS      current
    DESCRIPTION
       "The Link State ID is an LS Type Specific field
        containing either a Router ID or an IP Address;
        it identifies the piece of the  routing  domain
        that is being described by the advertisement."
    REFERENCE
       "OSPF Version 2, Section 12.1.4 Link State ID"
  ::= { rlOspfNetworkLsaEntry 3 }

rlOspfNetworkLsaRouterId OBJECT-TYPE
    SYNTAX      RouterID
    MAX-ACCESS  read-only
    STATUS      current
    DESCRIPTION
       "The 32 bit number that uniquely identifies the
        originating router in the Autonomous System."
    REFERENCE
       "OSPF Version 2, Appendix C.1 Global parameters"
  ::= { rlOspfNetworkLsaEntry 4 }

rlOspfNetworkLsaIdx OBJECT-TYPE
    SYNTAX      Unsigned32 (1.. 65535)
    MAX-ACCESS  read-only
    STATUS      current
    DESCRIPTION
       "The index is a unsigned 32-bit integer.
        It is used as sequence number of entry
        in the LSA and relevant only for Router
        or Network LSA which can contain
        unlimited number of entries."
  ::= { rlOspfNetworkLsaEntry 5 }

rlOspfNetworkLsaSequence OBJECT-TYPE
    SYNTAX      Integer32
    MAX-ACCESS  read-only
    STATUS      current
    DESCRIPTION
       "The sequence number field is a signed  32-bit
        integer. It is used to detect old and duplicate
        link state advertisements. The space of sequence
        numbers is linearly ordered. The larger the
        sequence number the more recent the advertisement."
    REFERENCE
       "OSPF Version 2, Section 12.1.6 LS sequence number"
  ::= { rlOspfNetworkLsaEntry 6 }


rlOspfNetworkLsaAge OBJECT-TYPE
    SYNTAX      Integer32    -- Should be 0..MaxAge
    MAX-ACCESS  read-only
    STATUS      current
    DESCRIPTION
       "This field is the age of the link state
        advertisement in seconds."
       REFERENCE
          "OSPF Version 2, Section 12.1.1 LS age"
  ::= { rlOspfNetworkLsaEntry 7 }

rlOspfNetworkLsaChecksum OBJECT-TYPE
    SYNTAX      Integer32
    MAX-ACCESS  read-only
    STATUS      current
    DESCRIPTION
       "This field is the checksum of the complete contents
        of the advertisement, excepting the age field.
        The age field is excepted so that an advertisement's
        age can be incremented without updating the checksum.
        The checksum used is the same that is used for ISO
        connectionless datagrams; it is commonly referred
        to as the Fletcher checksum."
    REFERENCE
       "OSPF Version 2, Section 12.1.7 LS checksum"
  ::= { rlOspfNetworkLsaEntry 8 }

rlOspfNetworkLsaLength OBJECT-TYPE
    SYNTAX      Unsigned32
    MAX-ACCESS  read-only
    STATUS      current
    DESCRIPTION
       "The lenth in bytes of the LSA.
        This includes the 20 byte LSA header."
  ::= { rlOspfNetworkLsaEntry 9 }

rlOspfNetworkLsaMask OBJECT-TYPE
    SYNTAX      IpAddress
    MAX-ACCESS  read-only
    STATUS      current
    DESCRIPTION
       "The IP address mask for the network."
  ::= { rlOspfNetworkLsaEntry 10 }

rlOspfNetworkLsaAttRouter OBJECT-TYPE
    SYNTAX      IpAddress
    MAX-ACCESS  read-only
    STATUS      current
    DESCRIPTION
       "The Router IDs of each of the routers
        attached to the network."
  ::= { rlOspfNetworkLsaEntry 11 }


------------------------------------------------------------------------------
--  OSPF Summary LSA (Type 3) Table
------------------------------------------------------------------------------

rlOspfSummaryType3LsaTable OBJECT-TYPE
    SYNTAX      SEQUENCE OF RlOspfSummaryType3LsaEntry
    MAX-ACCESS  not-accessible
    STATUS      current
    DESCRIPTION
        "Summary Link State Advertisement
         for network (Type 3)."
    ::= { rlOspfLsdb 3 }


rlOspfSummaryType3LsaEntry OBJECT-TYPE
    SYNTAX      RlOspfSummaryType3LsaEntry
    MAX-ACCESS  not-accessible
    STATUS      current
    DESCRIPTION
    "A single entry from Summary LSA."
    INDEX { rlOspfSummaryType3LsaProcessId, rlOspfSummaryType3LsaAreaId, rlOspfSummaryType3LsaLsid,
            rlOspfSummaryType3LsaRouterId}
       ::= { rlOspfSummaryType3LsaTable 1 }

RlOspfSummaryType3LsaEntry ::=
    SEQUENCE {
        rlOspfSummaryType3LsaProcessId
            RlOspfProcessID,
        rlOspfSummaryType3LsaAreaId
            AreaID,
        rlOspfSummaryType3LsaLsid
            IpAddress,
        rlOspfSummaryType3LsaRouterId
            RouterID,
        rlOspfSummaryType3LsaSequence
            Integer32,
        rlOspfSummaryType3LsaAge
            Integer32,
        rlOspfSummaryType3LsaChecksum
            Integer32,
        rlOspfSummaryType3LsaLength
            Unsigned32,
        rlOspfSummaryType3LsaMask
            IpAddress,
        rlOspfSummaryType3LsaMetric
            Unsigned32
}

rlOspfSummaryType3LsaProcessId OBJECT-TYPE
      SYNTAX   RlOspfProcessID
      MAX-ACCESS   read-only
      STATUS   current
      DESCRIPTION
         "A 32-bit integer uniquely identifying an OSPF process."
    ::= { rlOspfSummaryType3LsaEntry 1 }

rlOspfSummaryType3LsaAreaId OBJECT-TYPE
    SYNTAX      AreaID
    MAX-ACCESS  read-only
    STATUS      current
    DESCRIPTION
       "The 32 bit identifier of the Area  from  which
        the LSA was received."
    REFERENCE
       "OSPF Version 2, Appendix C.2 Area parameters"
  ::= { rlOspfSummaryType3LsaEntry 2 }

rlOspfSummaryType3LsaLsid OBJECT-TYPE
    SYNTAX      IpAddress
    MAX-ACCESS  read-only
    STATUS      current
    DESCRIPTION
       "The Link State ID is an LS Type Specific field
        containing either a Router ID or an IP Address;
        it identifies the piece of the  routing  domain
        that is being described by the advertisement."
    REFERENCE
       "OSPF Version 2, Section 12.1.4 Link State ID"
  ::= { rlOspfSummaryType3LsaEntry 3 }

rlOspfSummaryType3LsaRouterId OBJECT-TYPE
    SYNTAX      RouterID
    MAX-ACCESS  read-only
    STATUS      current
    DESCRIPTION
       "The 32 bit number that uniquely identifies the
        originating router in the Autonomous System."
    REFERENCE
       "OSPF Version 2, Appendix C.1 Global parameters"
  ::= { rlOspfSummaryType3LsaEntry 4 }

rlOspfSummaryType3LsaSequence OBJECT-TYPE
    SYNTAX      Integer32
    MAX-ACCESS  read-only
    STATUS      current
    DESCRIPTION
       "The sequence number field is a signed  32-bit
        integer. It is used to detect old and duplicate
        link state advertisements. The space of sequence
        numbers is linearly ordered. The larger the
        sequence number the more recent the advertisement."
    REFERENCE
       "OSPF Version 2, Section 12.1.6 LS sequence number"
  ::= { rlOspfSummaryType3LsaEntry 5 }


rlOspfSummaryType3LsaAge OBJECT-TYPE
    SYNTAX      Integer32    -- Should be 0..MaxAge
    MAX-ACCESS  read-only
    STATUS      current
    DESCRIPTION
       "This field is the age of the link state
        advertisement in seconds."
       REFERENCE
          "OSPF Version 2, Section 12.1.1 LS age"
  ::= { rlOspfSummaryType3LsaEntry 6 }

rlOspfSummaryType3LsaChecksum OBJECT-TYPE
    SYNTAX      Integer32
    MAX-ACCESS  read-only
    STATUS      current
    DESCRIPTION
       "This field is the checksum of the complete contents
        of the advertisement, excepting the age field.
        The age field is excepted so that an advertisement's
        age can be incremented without updating the checksum.
        The checksum used is the same that is used for ISO
        connectionless datagrams; it is commonly referred
        to as the Fletcher checksum."
    REFERENCE
       "OSPF Version 2, Section 12.1.7 LS checksum"
  ::= { rlOspfSummaryType3LsaEntry 7 }

rlOspfSummaryType3LsaLength OBJECT-TYPE
    SYNTAX      Unsigned32
    MAX-ACCESS  read-only
    STATUS      current
    DESCRIPTION
       "The lenth in bytes of the LSA.
        This includes the 20 byte LSA header."
  ::= { rlOspfSummaryType3LsaEntry 8 }

rlOspfSummaryType3LsaMask OBJECT-TYPE
    SYNTAX      IpAddress
    MAX-ACCESS  read-only
    STATUS      current
    DESCRIPTION
       "Value depends on the link's Type field."
  ::= { rlOspfSummaryType3LsaEntry 9 }

rlOspfSummaryType3LsaMetric OBJECT-TYPE
    SYNTAX      Unsigned32
    MAX-ACCESS  read-only
    STATUS      current
    DESCRIPTION
       "The cost of using this router link."
  ::= { rlOspfSummaryType3LsaEntry 10 }


------------------------------------------------------------------------------
--  OSPF Summary LSA (Type 4) Table
------------------------------------------------------------------------------

rlOspfSummaryType4LsaTable OBJECT-TYPE
    SYNTAX      SEQUENCE OF RlOspfSummaryType4LsaEntry
    MAX-ACCESS  not-accessible
    STATUS      current
    DESCRIPTION
        "Summary Link State Advertisement
         for ASBR (Type 4)."
    ::= { rlOspfLsdb 4 }


rlOspfSummaryType4LsaEntry OBJECT-TYPE
    SYNTAX      RlOspfSummaryType4LsaEntry
    MAX-ACCESS  not-accessible
    STATUS      current
    DESCRIPTION
    "A single entry from Summary LSA."
    INDEX { rlOspfSummaryType4LsaProcessId, rlOspfSummaryType4LsaAreaId, rlOspfSummaryType4LsaLsid,
            rlOspfSummaryType4LsaRouterId}
       ::= { rlOspfSummaryType4LsaTable 1 }

RlOspfSummaryType4LsaEntry ::=
    SEQUENCE {
        rlOspfSummaryType4LsaProcessId
            RlOspfProcessID,
        rlOspfSummaryType4LsaAreaId
            AreaID,
        rlOspfSummaryType4LsaLsid
            IpAddress,
        rlOspfSummaryType4LsaRouterId
            RouterID,
        rlOspfSummaryType4LsaSequence
            Integer32,
        rlOspfSummaryType4LsaAge
            Integer32,
        rlOspfSummaryType4LsaChecksum
            Integer32,
        rlOspfSummaryType4LsaLength
            Unsigned32,
        rlOspfSummaryType4LsaMetric
            Unsigned32
}

rlOspfSummaryType4LsaProcessId OBJECT-TYPE
      SYNTAX   RlOspfProcessID
      MAX-ACCESS   read-only
      STATUS   current
      DESCRIPTION
         "A 32-bit integer uniquely identifying an OSPF process."
    ::= { rlOspfSummaryType4LsaEntry 1 }

rlOspfSummaryType4LsaAreaId OBJECT-TYPE
    SYNTAX      AreaID
    MAX-ACCESS  read-only
    STATUS      current
    DESCRIPTION
       "The 32 bit identifier of the Area  from  which
        the LSA was received."
    REFERENCE
       "OSPF Version 2, Appendix C.2 Area parameters"
  ::= { rlOspfSummaryType4LsaEntry 2 }

rlOspfSummaryType4LsaLsid OBJECT-TYPE
    SYNTAX      IpAddress
    MAX-ACCESS  read-only
    STATUS      current
    DESCRIPTION
       "The Link State ID is an LS Type Specific field
        containing either a Router ID or an IP Address;
        it identifies the piece of the  routing  domain
        that is being described by the advertisement."
    REFERENCE
       "OSPF Version 2, Section 12.1.4 Link State ID"
  ::= { rlOspfSummaryType4LsaEntry 3 }

rlOspfSummaryType4LsaRouterId OBJECT-TYPE
    SYNTAX      RouterID
    MAX-ACCESS  read-only
    STATUS      current
    DESCRIPTION
       "The 32 bit number that uniquely identifies the
        originating router in the Autonomous System."
    REFERENCE
       "OSPF Version 2, Appendix C.1 Global parameters"
  ::= { rlOspfSummaryType4LsaEntry 4 }

rlOspfSummaryType4LsaSequence OBJECT-TYPE
    SYNTAX      Integer32
    MAX-ACCESS  read-only
    STATUS      current
    DESCRIPTION
       "The sequence number field is a signed  32-bit
        integer. It is used to detect old and duplicate
        link state advertisements. The space of sequence
        numbers is linearly ordered. The larger the
        sequence number the more recent the advertisement."
    REFERENCE
       "OSPF Version 2, Section 12.1.6 LS sequence number"
  ::= { rlOspfSummaryType4LsaEntry 5 }


rlOspfSummaryType4LsaAge OBJECT-TYPE
    SYNTAX      Integer32    -- Should be 0..MaxAge
    MAX-ACCESS  read-only
    STATUS      current
    DESCRIPTION
       "This field is the age of the link state
        advertisement in seconds."
       REFERENCE
          "OSPF Version 2, Section 12.1.1 LS age"
  ::= { rlOspfSummaryType4LsaEntry 6 }

rlOspfSummaryType4LsaChecksum OBJECT-TYPE
    SYNTAX      Integer32
    MAX-ACCESS  read-only
    STATUS      current
    DESCRIPTION
       "This field is the checksum of the complete contents
        of the advertisement, excepting the age field.
        The age field is excepted so that an advertisement's
        age can be incremented without updating the checksum.
        The checksum used is the same that is used for ISO
        connectionless datagrams; it is commonly referred
        to as the Fletcher checksum."
    REFERENCE
       "OSPF Version 2, Section 12.1.7 LS checksum"
  ::= { rlOspfSummaryType4LsaEntry 7 }

rlOspfSummaryType4LsaLength OBJECT-TYPE
    SYNTAX      Unsigned32
    MAX-ACCESS  read-only
    STATUS      current
    DESCRIPTION
       "The lenth in bytes of the LSA.
        This includes the 20 byte LSA header."
  ::= { rlOspfSummaryType4LsaEntry 8 }

rlOspfSummaryType4LsaMetric OBJECT-TYPE
    SYNTAX      Unsigned32
    MAX-ACCESS  read-only
    STATUS      current
    DESCRIPTION
       "The cost of using this router link."
  ::= { rlOspfSummaryType4LsaEntry 9 }


------------------------------------------------------------------------------
--  OSPF External LSA Table
------------------------------------------------------------------------------

rlOspfExternalLsaTable OBJECT-TYPE
    SYNTAX      SEQUENCE OF RlOspfExternalLsaEntry
    MAX-ACCESS  not-accessible
    STATUS      current
    DESCRIPTION
        "External Link State Advertisement."
    ::= { rlOspfLsdb 5 }


rlOspfExternalLsaEntry OBJECT-TYPE
    SYNTAX      RlOspfExternalLsaEntry
    MAX-ACCESS  not-accessible
    STATUS      current
    DESCRIPTION
    "A single entry from External LSA."
    INDEX { rlOspfExternalLsaProcessId, rlOspfExternalLsaLsid,
            rlOspfExternalLsaRouterId}
       ::= { rlOspfExternalLsaTable 1 }

RlOspfExternalLsaEntry ::=
    SEQUENCE {
        rlOspfExternalLsaProcessId
            RlOspfProcessID,
        rlOspfExternalLsaLsid
            IpAddress,
        rlOspfExternalLsaRouterId
            RouterID,
        rlOspfExternalLsaSequence
            Integer32,
        rlOspfExternalLsaAge
            Integer32,
        rlOspfExternalLsaChecksum
            Integer32,
        rlOspfExternalLsaLength
            Unsigned32,
        rlOspfExternalLsaMask
            IpAddress,
        rlOspfExternalLsaFrwAddress
            IpAddress,
        rlOspfExternalLsaBitE
            INTEGER,
        rlOspfExternalLsaMetric
            Unsigned32,
        rlOspfExternalLsaTag
            Unsigned32
}

rlOspfExternalLsaProcessId OBJECT-TYPE
      SYNTAX   RlOspfProcessID
      MAX-ACCESS   read-only
      STATUS   current
      DESCRIPTION
         "A 32-bit integer uniquely identifying an OSPF process."
    ::= { rlOspfExternalLsaEntry 1 }

rlOspfExternalLsaLsid OBJECT-TYPE
    SYNTAX      IpAddress
    MAX-ACCESS  read-only
    STATUS      current
    DESCRIPTION
       "The Link State ID is an LS Type Specific field
        containing either a Router ID or an IP Address;
        it identifies the piece of the  routing  domain
        that is being described by the advertisement."
    REFERENCE
       "OSPF Version 2, Section 12.1.4 Link State ID"
  ::= { rlOspfExternalLsaEntry 2 }

rlOspfExternalLsaRouterId OBJECT-TYPE
    SYNTAX      RouterID
    MAX-ACCESS  read-only
    STATUS      current
    DESCRIPTION
       "The 32 bit number that uniquely identifies the
        originating router in the Autonomous System."
    REFERENCE
       "OSPF Version 2, Appendix C.1 Global parameters"
  ::= { rlOspfExternalLsaEntry 3 }

rlOspfExternalLsaSequence OBJECT-TYPE
    SYNTAX      Integer32
    MAX-ACCESS  read-only
    STATUS      current
    DESCRIPTION
       "The sequence number field is a signed  32-bit
        integer. It is used to detect old and duplicate
        link state advertisements. The space of sequence
        numbers is linearly ordered. The larger the
        sequence number the more recent the advertisement."
    REFERENCE
       "OSPF Version 2, Section 12.1.6 LS sequence number"
  ::= { rlOspfExternalLsaEntry 4 }

rlOspfExternalLsaAge OBJECT-TYPE
    SYNTAX      Integer32    -- Should be 0..MaxAge
    MAX-ACCESS  read-only
    STATUS      current
    DESCRIPTION
       "This field is the age of the link state
        advertisement in seconds."
       REFERENCE
          "OSPF Version 2, Section 12.1.1 LS age"
  ::= { rlOspfExternalLsaEntry 5 }

rlOspfExternalLsaChecksum OBJECT-TYPE
    SYNTAX      Integer32
    MAX-ACCESS  read-only
    STATUS      current
    DESCRIPTION
       "This field is the checksum of the complete contents
        of the advertisement, excepting the age field.
        The age field is excepted so that an advertisement's
        age can be incremented without updating the checksum.
        The checksum used is the same that is used for ISO
        connectionless datagrams; it is commonly referred
        to as the Fletcher checksum."
    REFERENCE
       "OSPF Version 2, Section 12.1.7 LS checksum"
  ::= { rlOspfExternalLsaEntry 6 }

rlOspfExternalLsaLength OBJECT-TYPE
    SYNTAX      Unsigned32
    MAX-ACCESS  read-only
    STATUS      current
    DESCRIPTION
       "The lenth in bytes of the LSA.
        This includes the 20 byte LSA header."
  ::= { rlOspfExternalLsaEntry 7 }

rlOspfExternalLsaMask OBJECT-TYPE
    SYNTAX      IpAddress
    MAX-ACCESS  read-only
    STATUS      current
    DESCRIPTION
       "Value depends on the link's Type field."
  ::= { rlOspfExternalLsaEntry 8 }

rlOspfExternalLsaFrwAddress OBJECT-TYPE
    SYNTAX      IpAddress
    MAX-ACCESS  read-only
    STATUS      current
    DESCRIPTION
       "Data traffic for the advertised destination
        will be forwarded to this address. If the
        Forwarding address is set to 0.0.0.0, data
        traffic will be forwarded instead to the LSA's
        originator (i.e., the responsible AS boundary router)."
  ::= { rlOspfExternalLsaEntry 9 }

rlOspfExternalLsaBitE OBJECT-TYPE
    SYNTAX INTEGER {
        off(1),
        on(2)
    }
    MAX-ACCESS   read-only
        STATUS   current
    DESCRIPTION
       "The type of external metric. If bit E is set,
        the metric specified is a Type 2 external metric."
  ::= { rlOspfExternalLsaEntry 10 }

rlOspfExternalLsaMetric OBJECT-TYPE
    SYNTAX      Unsigned32
    MAX-ACCESS  read-only
    STATUS      current
    DESCRIPTION
       "The cost of this route."
  ::= { rlOspfExternalLsaEntry 11 }

rlOspfExternalLsaTag OBJECT-TYPE
    SYNTAX      Unsigned32
    MAX-ACCESS  read-only
    STATUS      current
    DESCRIPTION
       "A 32-bit field attached to each external route."
  ::= { rlOspfExternalLsaEntry 12 }

END
