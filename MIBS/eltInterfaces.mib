ELTEX-MES-eltInterfaces DEFINITIONS ::= BEGIN

-- Title:      ELTEX MES Switch Interfaces Private
-- Version:    1.3
-- Date:       6 Jun 2022
-- 14-Aug-2012 - Added SFP operation mode
-- 28-Feb-2017 - Added eltSwIfAutoNegotiationBypass
-- 25-Sep-2019 - Added "forced" value for the eltSwIfAutoNegotiationBypass field.
-- 14-Apr-2021 - Added eltSwIfFecAdminMode and eltSwIfFecOperMode
-- 06-Jun-2022 - Added eltSwIfUnidirectional

IMPORTS
    eltMesSwInterfaces                                      FROM ELTEX-MES
    OBJECT-TYPE                                             FROM SNMPv2-SMI
    Counter                                                 FROM RFC1155-SMI;

eltSwIfTable OBJECT-TYPE
   SYNTAX  SEQUENCE OF EltSwIfEntry
   MAX-ACCESS   not-accessible
   STATUS       current
   DESCRIPTION
        "Switch media specific information and configuration of the device
         interfaces."
   ::= { eltMesSwInterfaces 1 }

eltSwIfEntry OBJECT-TYPE
   SYNTAX  EltSwIfEntry
   MAX-ACCESS   not-accessible
   STATUS       current
   DESCRIPTION
        "Defines the contents of each line in the eltSwIfTable table."
   INDEX   { eltSwIfIndex }
   ::= { eltSwIfTable 1 }

EltSwIfEntry ::= SEQUENCE {
   eltSwIfIndex               INTEGER,
   eltSwIfSfpOperationMode    INTEGER,
   eltSwIfAutoNegotiationBypass INTEGER,
   eltSwIfFecAdminMode        INTEGER,
   eltSwIfFecOperMode         INTEGER,
   eltSwIfUnidirectional      INTEGER
}

eltSwIfIndex OBJECT-TYPE
    SYNTAX   INTEGER
    MAX-ACCESS  read-only
    STATUS      current
    DESCRIPTION
        "Index to the eltSwIfTable. The interface defined by a
         particular value of this index is the same interface as
         identified by the same value of ifIndex (MIB II)."
    ::= { eltSwIfEntry 1 }

eltSwIfSfpOperationMode OBJECT-TYPE
    SYNTAX  INTEGER {
        fiber(0),
        directAttach(1),
        copperSfp(2),
        unknown(3)
    }
    MAX-ACCESS  read-write
    STATUS      current
    DESCRIPTION
        "This variable indicates plugged in SFP transceiver operation mode."
    DEFVAL { unknown }
    ::= { eltSwIfEntry 2 }

eltSwIfAutoNegotiationBypass OBJECT-TYPE
   SYNTAX  INTEGER {
        enabled(1),
        disabled(2),
        forced(3)
   }
   MAX-ACCESS   read-write
   STATUS       current
   DESCRIPTION
       "When enabled the link can be established by bypassing the Auto-Negotiation procedure
        if the link partner doesn't respond to the Auto-Negotiation process."
    ::= {  eltSwIfEntry 3  }

eltSwIfFecAdminMode OBJECT-TYPE
   SYNTAX  INTEGER {
        disabled(0),
        auto(1),
        cl74(2),
        cl91(3)
   }
   MAX-ACCESS   read-write
   STATUS       current
   DESCRIPTION
       "This variable controls the Forward Error Correction (FEC) mode 
        on the port."
   ::= { eltSwIfEntry 12 }

eltSwIfFecOperMode OBJECT-TYPE
   SYNTAX  INTEGER {
        disabled(0),
        auto(1),
        cl74(2),
        cl91(3)
   }
   MAX-ACCESS   read-only
   STATUS       current
   DESCRIPTION
       "This variable indicates the actual Forward Error Correction (FEC) mode 
        that currently in use on the port."
   ::= { eltSwIfEntry 13 }


eltSwIfUnidirectional OBJECT-TYPE
    SYNTAX  INTEGER {
        disable(0),
        send-only(1)
    }
    MAX-ACCESS   read-write
    STATUS       current
    DESCRIPTION
        "This variable controls the Unidirectional mode on the port."
    DEFVAL { disable }
    ::= { eltSwIfEntry 15 }

--
-- Ports utilization table mib
--
eltSwIfUtilizationTable OBJECT-TYPE
   SYNTAX  SEQUENCE  OF EltSwIfUtilizationEntry
   MAX-ACCESS   not-accessible
   STATUS       current
   DESCRIPTION
    "Switch ports utilization configuration and information."
   ::=  { eltMesSwInterfaces 2 }

eltSwIfUtilizationEntry OBJECT-TYPE
   SYNTAX  EltSwIfUtilizationEntry
   MAX-ACCESS   not-accessible
   STATUS       current
   DESCRIPTION
    "Defines the contents of each line in the eltSwIfUtilizationTable table."
   INDEX   { eltSwIfUtilizationIfIndex }
   ::=  { eltSwIfUtilizationTable 1 }

EltSwIfUtilizationEntry ::= SEQUENCE {
        eltSwIfUtilizationIfIndex               INTEGER,
        eltSwIfUtilizationAverageTime           INTEGER,
        eltSwIfUtilizationCurrentInPkts         Counter,
        eltSwIfUtilizationCurrentInRate         Counter,
        eltSwIfUtilizationCurrentOutPkts        Counter,
        eltSwIfUtilizationCurrentOutRate        Counter,
        eltSwIfUtilizationAverageInPkts         Counter,
        eltSwIfUtilizationAverageInRate         Counter,
        eltSwIfUtilizationAverageOutPkts        Counter,
        eltSwIfUtilizationAverageOutRate        Counter
        }

eltSwIfUtilizationIfIndex OBJECT-TYPE
   SYNTAX  INTEGER
   MAX-ACCESS  read-only
   STATUS  current
   DESCRIPTION
          "A unique value for each interface.  Its value
          ranges between 1 and the value of ifNumber.  The
          value for each interface must remain constant at
          least from one re-initialization of the entity's
          network management system to the next re-
          initialization."
   ::= { eltSwIfUtilizationEntry 1 }

eltSwIfUtilizationAverageTime OBJECT-TYPE
   SYNTAX  INTEGER
   MAX-ACCESS  read-write
   STATUS  current
   DESCRIPTION
          "An average load time in seconds for which interface
          utilization is calculated."
   ::= { eltSwIfUtilizationEntry 2 }

eltSwIfUtilizationCurrentInPkts OBJECT-TYPE
   SYNTAX  Counter
   MAX-ACCESS  read-only
   STATUS  current
   DESCRIPTION
          "The total number of all (UC, MC and BC) packets
          received on the interface during last 5 seconds."
  ::= { eltSwIfUtilizationEntry 3 }

eltSwIfUtilizationCurrentInRate OBJECT-TYPE
   SYNTAX  Counter
   MAX-ACCESS  read-only
   STATUS  current
   DESCRIPTION
          "The inbound rate in kbit/sec
          on the interface during last 5 seconds."
  ::= { eltSwIfUtilizationEntry 4 }

eltSwIfUtilizationCurrentOutPkts OBJECT-TYPE
   SYNTAX  Counter
   MAX-ACCESS  read-only
   STATUS  current
   DESCRIPTION
          "The total number of all (UC, MC and BC) packets
          sent out of the interface during last 5 seconds."
  ::= { eltSwIfUtilizationEntry 5 }

eltSwIfUtilizationCurrentOutRate OBJECT-TYPE
   SYNTAX  Counter
   MAX-ACCESS  read-only
   STATUS  current
   DESCRIPTION
          "The outbound rate in kbit/sec
          on the interface during last 5 seconds."
  ::= { eltSwIfUtilizationEntry 6 }

eltSwIfUtilizationAverageInPkts OBJECT-TYPE
   SYNTAX  Counter
   MAX-ACCESS  read-only
   STATUS  current
   DESCRIPTION
          "The total number of all (UC, MC and BC) packets
          received on the interface during configured
          load average time for this interface."
  ::= { eltSwIfUtilizationEntry 7 }

eltSwIfUtilizationAverageInRate OBJECT-TYPE
   SYNTAX  Counter
   MAX-ACCESS  read-only
   STATUS  current
   DESCRIPTION
          "The inbound rate in kbit/sec on the interface
          during configured load average time for this interface."
  ::= { eltSwIfUtilizationEntry 8 }

eltSwIfUtilizationAverageOutPkts OBJECT-TYPE
   SYNTAX  Counter
   MAX-ACCESS  read-only
   STATUS  current
   DESCRIPTION
          "The total number of all (UC, MC and BC) packets
          sent out of the interface during configured
          load average time for this interface."
  ::= { eltSwIfUtilizationEntry 9 }

eltSwIfUtilizationAverageOutRate OBJECT-TYPE
   SYNTAX  Counter
   MAX-ACCESS  read-only
   STATUS  current
   DESCRIPTION
          "The outbound rate in kbit/sec on the interface
          during configured load average time for this interface."
  ::= { eltSwIfUtilizationEntry 10 }

END
