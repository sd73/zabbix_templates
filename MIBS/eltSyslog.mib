ELTEX-MES-SYSLOG-MIB DEFINITIONS ::= BEGIN

-- Title:      ELTEX MES SYSLOG Private MIB
-- Version:    2.1
-- Date:       31 Mar 2020
--
-- 11-May-2016 Added eltSyslogCpuRateLimiterTable
-- 31-Mar-2016 Added eltSyslogUserCmdEnable

IMPORTS
    eltMes                                  FROM ELTEX-MES
    OBJECT-TYPE, MODULE-IDENTITY            FROM SNMPv2-SMI
    EltCpuRateLimiterTrafficType            FROM ELTEX-MES-SWITCH-RATE-LIMITER-MIB
    rlSyslogLogEntry                        FROM RADLAN-SYSLOG-MIB
    DisplayString, TEXTUAL-CONVENTION,
    TruthValue                              FROM SNMPv2-TC;

eltMesSyslog MODULE-IDENTITY
          LAST-UPDATED "202003310000Z"
          ORGANIZATION "Eltex Ltd."
          CONTACT-INFO
                  "eltex.nsk.ru"
          DESCRIPTION
                  "The private MIB module definition for SYSLOG services in Eltex devices."
          ::= { eltMes 10 }

eltSyslogCpuRateLimiterTable OBJECT-TYPE
    SYNTAX          SEQUENCE OF EltSyslogCpuRateLimiterEntry
    MAX-ACCESS      not-accessible
    STATUS          current
    DESCRIPTION        "Enable/disable logging per CPU rate limiter."
    ::= { eltMesSyslog 1 }

eltSyslogCpuRateLimiterEntry OBJECT-TYPE
    SYNTAX          EltSyslogCpuRateLimiterEntry
    MAX-ACCESS      not-accessible
    STATUS          current
    DESCRIPTION        "An entry containing enable/disable logging settings per CPU rate limiter."
    INDEX           { eltSyslogCpuRateLimiterIndex }
    ::= { eltSyslogCpuRateLimiterTable 1 }

EltSyslogCpuRateLimiterEntry ::= SEQUENCE {
        eltSyslogCpuRateLimiterIndex       EltCpuRateLimiterTrafficType,
        eltSyslogCpuRateLimiterEnabled     TruthValue
}

eltSyslogCpuRateLimiterIndex OBJECT-TYPE
    SYNTAX          EltCpuRateLimiterTrafficType
    MAX-ACCESS      read-only
    STATUS          current
    DESCRIPTION        "Traffic type"
    ::= { eltSyslogCpuRateLimiterEntry 1 }

eltSyslogCpuRateLimiterEnabled OBJECT-TYPE
    SYNTAX          TruthValue
    MAX-ACCESS      read-write
    STATUS          current
    DESCRIPTION        "Enable logging of rate-limiter events"
    ::= { eltSyslogCpuRateLimiterEntry 2 }

--
-- eltMesSyslogEvents
--

eltMesSyslogEvents  OBJECT IDENTIFIER
    ::= { eltMesSyslog 2 }

--
-- eltSyslogEventsStpTable
--

eltSyslogEventsStpTable OBJECT-TYPE
    SYNTAX          SEQUENCE OF EltSyslogEventsStpEntry
    MAX-ACCESS      read-write
    STATUS          current
    DESCRIPTION        "Enable/disable logging of STP events."
    ::= { eltMesSyslogEvents 2 }

EltSyslogEventsStpEventType ::= TEXTUAL-CONVENTION
    STATUS current
    DESCRIPTION    "Types of STP events."
    SYNTAX INTEGER {
        eltSyslogEventsStpEventStateChange(1),
        eltSyslogEventsStpEventTopologyChange(2),
        eltSyslogEventsStpEventRootBridgeChange(3),
        eltSyslogEventsStpTcProtectionThresholdReached(4)
}

EltSyslogEventsStpEntry ::= SEQUENCE {
    eltSyslogEventsStpEventIndex        EltSyslogEventsStpEventType,
    eltSyslogEventsStpEventEnabled      TruthValue
}

eltSyslogEventsStpEntry OBJECT-TYPE
    SYNTAX          EltSyslogEventsStpEntry
    MAX-ACCESS      read-write
    STATUS          current
    DESCRIPTION        "An entry containing enable/disable logging of STP events."
    INDEX           { eltSyslogEventsStpEventIndex }
    ::= { eltSyslogEventsStpTable 1 }

eltSyslogEventsStpEventIndex OBJECT-TYPE
    SYNTAX          EltSyslogEventsStpEventType
    MAX-ACCESS      read-write
    STATUS          current
    DESCRIPTION         "Specify the index of STP event."
    ::= { eltSyslogEventsStpEntry 1 }

eltSyslogEventsStpEventEnabled OBJECT-TYPE
    SYNTAX          TruthValue
    MAX-ACCESS      read-write
    STATUS          current
    DESCRIPTION         "Enable logging of STP event."
    ::= { eltSyslogEventsStpEntry 2 }

eltSyslogUserCmdEnable OBJECT-TYPE
    SYNTAX  TruthValue
    MAX-ACCESS  read-write
    STATUS  current
    DESCRIPTION
        "User commands enter enable for syslog flash, syslog cache and syslog UDP.
         When set to true, generating syslog entry for user commands entered."
    DEFVAL  { false }
    ::= { eltMesSyslog 3 }
    
--
-- eltMesSyslogLogTable
--

eltMesSyslogLog OBJECT IDENTIFIER
    ::= { eltMesSyslog 5 }

eltMesSyslogLogTable OBJECT-TYPE
    SYNTAX      SEQUENCE OF EltMesSyslogLogEntry
    MAX-ACCESS  not-accessible
    STATUS      current
    DESCRIPTION
        "A table containing events sent to the system log file."
    ::= { eltMesSyslogLog 1 }

eltMesSyslogLogEntry OBJECT-TYPE
    SYNTAX      EltMesSyslogLogEntry
    MAX-ACCESS  not-accessible
    STATUS      current
    DESCRIPTION
        "A log entry "
    AUGMENTS   { rlSyslogLogEntry }
    ::= { eltMesSyslogLogTable 1 }

EltMesSyslogLogEntry ::=
    SEQUENCE {
        eltMesSyslogLogText1            DisplayString,
        eltMesSyslogLogText2            DisplayString
    }

eltMesSyslogLogText1 OBJECT-TYPE
    SYNTAX  DisplayString (SIZE(0..160))
    MAX-ACCESS  read-only
    STATUS  current
    DESCRIPTION
        "The text of the logged message without time and date - part 5."
    ::= { eltMesSyslogLogEntry 1 }

eltMesSyslogLogText2 OBJECT-TYPE
    SYNTAX  DisplayString (SIZE(0..160))
    MAX-ACCESS  read-only
    STATUS  current
    DESCRIPTION
        "The text of the logged message without time and date - part 6."
    ::= { eltMesSyslogLogEntry 2 }

END
