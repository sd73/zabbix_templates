RADLAN-BOOTP-MIB DEFINITIONS ::= BEGIN

-- Title:                RADLAN ROS
--                       Private BOOT P MIB
-- Version:              7.46
-- Date:                 15-Jan-2007

IMPORTS
    rnd                                                     FROM RADLAN-MIB
    OBJECT-TYPE, MODULE-IDENTITY, IpAddress                 FROM SNMPv2-SMI
    TruthValue, RowStatus, DisplayString                    FROM SNMPv2-TC
    InterfaceIndex, ifIndex                                 FROM IF-MIB
    SnmpAdminString                                         FROM SNMP-FRAMEWORK-MIB;

rndBootP MODULE-IDENTITY
                LAST-UPDATED "200701020000Z"
                ORGANIZATION "Marvell Semiconductor, Inc."
                CONTACT-INFO
					"5488 Marvell Lane
					Santa Clara, CA 95054
					USA

					Website:  www.marvell.com"
                DESCRIPTION
                      "This private MIB module defines boot p private MIBs."
                REVISION "200701020000Z"
                DESCRIPTION
                      "Initial revision."
        ::= { rnd 24 }

rndBootPServerAddress  OBJECT-TYPE
    SYNTAX IpAddress
    MAX-ACCESS read-write
    STATUS current
    DESCRIPTION
     " The IPAddress of the BOOTP server. the OpenGate will act as a BootP relay if
       this parameter is not equale to 0.0.0.0."
    DEFVAL  {'00000000'H}
      ::= { rndBootP 1 }

rndBootPRelaySecThreshold OBJECT-TYPE
    SYNTAX INTEGER
    MAX-ACCESS read-write
    STATUS current
    DESCRIPTION
       "BootP requests are relayed only if their SEC field is greater or
        equal to the threshold value in order to allow local BootP Servers
        to answer first."
    ::= { rndBootP 2 }

rndBootPActionTable OBJECT-TYPE
    SYNTAX     SEQUENCE OF RndBootPActionEntry
    MAX-ACCESS     not-accessible
    STATUS     current
    DESCRIPTION
            " The (conceptual) table mentione IP address which must be
              released/renewed on the interface."
    ::= { rndBootP 3 }

rndBootPActionEntry OBJECT-TYPE
    SYNTAX     RndBootPActionEntry
    MAX-ACCESS     not-accessible
    STATUS     current
    DESCRIPTION
            "An entry (conceptual row) in rndBootPActionTable."
    INDEX      { rndBootPActionIfIndex }
    ::= { rndBootPActionTable 1 }

RndBootPActionEntry ::= SEQUENCE {
    rndBootPActionIfIndex            InterfaceIndex,
    rndBootPActionStatus             RowStatus,
    rndBootPActionHostName           SnmpAdminString
}

rndBootPActionIfIndex          OBJECT-TYPE
    SYNTAX             InterfaceIndex
    MAX-ACCESS         read-only
    STATUS      current
    DESCRIPTION
        " The interface which the action is implemented for
        or NULL if it implemented for all device. "
    ::= { rndBootPActionEntry  1 }

rndBootPActionStatus OBJECT-TYPE
    SYNTAX     RowStatus
    MAX-ACCESS     read-create
    STATUS     current
    DESCRIPTION
            "The status of this entry.  Creating the entry renewing Bootp
              address on the interface; destroying the entry release Bootp
              address on the interface."
    ::= { rndBootPActionEntry   2}

rndBootPActionHostName OBJECT-TYPE
    SYNTAX SnmpAdminString (SIZE(0..20))
    MAX-ACCESS read-create
    STATUS current
    DESCRIPTION
       " This option specifies the name of the client."
    ::= { rndBootPActionEntry   3 }


END
