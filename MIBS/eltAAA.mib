ELTEX-MES-AAA DEFINITIONS ::= BEGIN

-- Title:      ELTEX MES AAA Extension Private
-- Version:    1.0
-- Date:       15 Sep 2020
--

IMPORTS
    eltMes, eltMesRadius, eltMesTacacs    FROM ELTEX-MES
    OBJECT-TYPE                           FROM SNMPv2-SMI
    TruthValue                            FROM SNMPv2-TC
    RlAAAAccountingMethod                 FROM RADLAN-AAA;

--
-- AAA MIB
--

eltMesAAA MODULE-IDENTITY
        LAST-UPDATED "201509210000Z"
        ORGANIZATION "Eltex Ltd."
        CONTACT-INFO
                "http://www.eltex.nsk.ru"
        DESCRIPTION
                "The private MIB module definition for Authentication, Authorization and Accounting
                 in Eltex MES devices."
        ::= { eltMes 79 }

EltAAAServiceType  ::= TEXTUAL-CONVENTION
   STATUS current
   DESCRIPTION    "Line service type."
   SYNTAX INTEGER {
      console(0),
      telnet(1),
      ssh(2)
}

EltAAAMethodListModeType ::= TEXTUAL-CONVENTION
   STATUS current
   DESCRIPTION    "Authentication mode type."
   SYNTAX INTEGER {
      eltAAAMethodListModeTypeChain(0),
      eltAAAMethodListModeTypeBreak(1)
}

eltAAAMethodListMode OBJECT-TYPE
    SYNTAX   EltAAAMethodListModeType
    MAX-ACCESS   read-write
    STATUS   current
    DESCRIPTION "Specify the authentication mode."
  ::= { eltMesAAA 1 }

eltAAAAccountingCommandsMethod OBJECT-TYPE
    SYNTAX   RlAAAAccountingMethod
    MAX-ACCESS   read-write
    STATUS   current
    DESCRIPTION "Specify a method used for accounting of user commands."
  ::= { eltMesAAA 2 }

--
-- Command Authorization MIB Objects
--
eltAAAAuthorizationCommandsMethodListName OBJECT-TYPE
    SYNTAX   OCTET STRING (SIZE(3..20))
    MAX-ACCESS   read-write
    STATUS   current
    DESCRIPTION "Specify a method used for authorization of user commands."
    DESCRIPTION "Specify the name of authorization list used for authorization of user commands."
    DEFVAL { "cmd_default" }
  ::= { eltMesAAA 5 }

--
-- RADIUS attributes
--

eltMesRadiusAttr OBJECT IDENTIFIER ::= { eltMesRadius 1 }

eltRadiusAttrNasIdAccessEnable OBJECT-TYPE
    SYNTAX      TruthValue
    MAX-ACCESS  read-write
    STATUS      current
    DESCRIPTION
        "Enable or disable including NAS-Identifier attribute in Access Request messages"
    DEFVAL      { false }
    ::= { eltMesRadiusAttr 1 }

eltRadiusAttrNasIdFormatString OBJECT-TYPE
    SYNTAX      OCTET STRING (SIZE(0..32))
    MAX-ACCESS  read-write
    STATUS      current
    DESCRIPTION
        "The format string for NAS-Identifier RADIUS attribute."
    DEFVAL      { "%h" }
    ::= { eltMesRadiusAttr 2 }

--
-- TACACS attributes
--

eltMesTacacsAttr OBJECT IDENTIFIER ::= { eltMesTacacs 1 }

eltTacacsAttrPortConfigTable OBJECT-TYPE
    SYNTAX      SEQUENCE OF EltTacacsAttrPortConfigEntry
    MAX-ACCESS  not-accessible
    STATUS      current
    DESCRIPTION
        "A list of TACACS attributes configuring mechanism."
    ::= { eltMesTacacsAttr 1 }

eltTacacsAttrPortConfigEntry OBJECT-TYPE
   SYNTAX      EltTacacsAttrPortConfigEntry
   MAX-ACCESS  not-accessible
   STATUS      current
   DESCRIPTION
       "An entry containing TACACS attributes configuring
        mechanism."
   INDEX { eltTacacsAttrPortLineType }
   ::= { eltTacacsAttrPortConfigTable 1 }

EltTacacsAttrPortConfigEntry ::=
    SEQUENCE {
        eltTacacsAttrPortLineType
            EltAAAServiceType,
        eltTacacsAttrPortFormat
            OCTET STRING
    }

eltTacacsAttrPortLineType OBJECT-TYPE
    SYNTAX      EltAAAServiceType
    MAX-ACCESS  not-accessible
    STATUS      current
    DESCRIPTION
        "Line type."
    ::= { eltTacacsAttrPortConfigEntry 1 }

eltTacacsAttrPortFormat OBJECT-TYPE
    SYNTAX      OCTET STRING
    MAX-ACCESS  read-write
    STATUS      current
    DESCRIPTION
        "User defined string to use as port attribute
         in TACACS packets. Specify port
         string template:
              <%n: line session index>,
              <%%: single %>."
    ::= { eltTacacsAttrPortConfigEntry 2 }

END
