RADLAN-rlDvmrp-MIB DEFINITIONS ::= BEGIN

-- Title:      RADLAN LCLI MIB
-- Version:    7.46
-- Date:       15-Jan-2007
--
-- 10-Nov-2004 Used rndNotifications instead of 0
-- 15-Jan-2007 Devided file appolo.txt to a few files
--             Renamed file appolo.txt to ralan-mib.mib

IMPORTS
    rnd, rndNotifications                                 FROM RADLAN-MIB
    rlIPmulticast                                        FROM RADLAN-rlIPMulticast-MIB
    dvmrpRouteNextHopEntry, dvmrpRouteNextHopSource,
    dvmrpRouteNextHopSourceMask, dvmrpRouteNextHopIfIndex
                                                         FROM DVMRP-STD-MIB

    TruthValue, DisplayString, RowStatus                 FROM SNMPv2-TC
    Unsigned32, TimeTicks,
    IpAddress                                            FROM SNMPv2-SMI
    MODULE-IDENTITY, OBJECT-TYPE                         FROM SNMPv2-SMI
    rndErrorDesc, rndErrorSeverity                       FROM RADLAN-DEVICEPARAMS-MIB;

-- { rlDvmrp 1 } Temporary reserved for dvmrpStdMIB

rlDvmrp       MODULE-IDENTITY
              LAST-UPDATED "200404190000Z"
              ORGANIZATION "Marvell Semiconductor, Inc."
              CONTACT-INFO
					"5488 Marvell Lane
					Santa Clara, CA 95054
					USA

					Website:  www.marvell.com"
              DESCRIPTION
                      "The private MIB module definition for IP Multicast DVMRP support in Radlan devices."
              REVISION "200404190000Z"
              DESCRIPTION
                      "Initial version of this MIB."
          ::= { rlIPmulticast  4 }


rlDvmrpMibVersion OBJECT-TYPE
    SYNTAX  INTEGER
    MAX-ACCESS  read-only
    STATUS  current
    DESCRIPTION
        "MIB's version, the current version is 1."
    ::= { rlDvmrp 2 }

rlDvmrpEnable OBJECT-TYPE
    SYNTAX      INTEGER { enabled(1), disabled(2) }
    MAX-ACCESS  read-write
    STATUS      current
    DESCRIPTION
        "The enabled status of Dvmrp on this router."
::= { rlDvmrp 3 }

rlDvmrpProbeInterval OBJECT-TYPE
    SYNTAX      INTEGER
    UNITS       "seconds"
    MAX-ACCESS  read-write
    STATUS      current
    DESCRIPTION
        "The default interval at which periodic DVMRP Probe
         messages are to be sent."
    DEFVAL     { 10 }
::= { rlDvmrp 4 }

rlDvmrpNeighborTimeOutInterval OBJECT-TYPE
    SYNTAX      INTEGER (25..400)
    UNITS       "seconds"
    MAX-ACCESS  read-write
    STATUS      current
    DESCRIPTION
        "The default interval, if expired the Neighbor need to be
         deleted from Interface."
    DEFVAL     { 35 }
::= { rlDvmrp 5 }

rlDvmrpMinFlashUpdateInterval OBJECT-TYPE
    SYNTAX      INTEGER
    UNITS       "seconds"
    MAX-ACCESS  read-write
    STATUS      current
    DESCRIPTION
        "The min interval at which the DVMRP Fash (Report msg)
         messages are to be sent."
    DEFVAL { 5 }
::= { rlDvmrp 6 }

rlDvmrpRouteReportInterval OBJECT-TYPE
    SYNTAX     INTEGER
    UNITS         "seconds"
    MAX-ACCESS  read-write
    STATUS      current
    DESCRIPTION
        "The default interval at which periodic DVMRP Report messages are to be sent."
    DEFVAL     { 60 }
::= { rlDvmrp 7 }

rlDvmrpRouteExpirationTime OBJECT-TYPE
    SYNTAX      INTEGER
    UNITS          "seconds"
    MAX-ACCESS   read-write
    STATUS       current
    DESCRIPTION
        "The default interval at which route expired."
    DEFVAL  { 140 }
::= { rlDvmrp 8 }

rlDvmrpPruneLifetime OBJECT-TYPE
    SYNTAX      INTEGER (200..7200)
    UNITS       "seconds"
    MAX-ACCESS  read-write
    STATUS      current
    DESCRIPTION
        "The default value of prune interval to be send upstream."
    DEFVAL { 200 }
::= { rlDvmrp 9 }

rlDvmrpRouteDesignatedForwarderExtTable OBJECT-TYPE
    SYNTAX     SEQUENCE OF RlDvmrpRouteDesignatedForwarderExtEntry
    MAX-ACCESS not-accessible
    STATUS     current
    DESCRIPTION
            "The (conceptual) table listing the designated forwarder
            for each source mask and interface."
    ::= { rlDvmrp 10}

rlDvmrpRouteDesignatedForwarderExtEntry  OBJECT-TYPE
    SYNTAX     RlDvmrpRouteDesignatedForwarderExtEntry
    MAX-ACCESS not-accessible
    STATUS     current
    DESCRIPTION
            "An entry (conceptual row) in the rlDvmrpRouteDesignatedForwarderExtTable.
            Specifies the designated forwarder for this source mask and interface."
    AUGMENTS      { dvmrpRouteNextHopEntry }
    ::= { rlDvmrpRouteDesignatedForwarderExtTable 1 }

RlDvmrpRouteDesignatedForwarderExtEntry  ::= SEQUENCE {
    rlDvmrpRouteDesignatedForwarder      IpAddress
}

rlDvmrpRouteDesignatedForwarder   OBJECT-TYPE
    SYNTAX     IpAddress
    MAX-ACCESS read-only
    STATUS     current
    DESCRIPTION
            "The address of the designated forwarder
            for the specific Source Mask and Interface."
    ::= { rlDvmrpRouteDesignatedForwarderExtEntry  1 }


 rlDvmrpTableOverflow NOTIFICATION-TYPE
      OBJECTS {
        rndErrorDesc,
        rndErrorSeverity
      }
      STATUS  current
      DESCRIPTION
          "A DVMRP Table overflows."
      ::= { rndNotifications 155 }





END
