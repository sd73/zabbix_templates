ELTEX-MES-eltMacNotification-MIB DEFINITIONS ::= BEGIN

IMPORTS
        MODULE-IDENTITY, OBJECT-TYPE, NOTIFICATION-TYPE, Integer32
                FROM SNMPv2-SMI
        TruthValue, TimeStamp, MacAddress, TEXTUAL-CONVENTION
                FROM SNMPv2-TC
        ifIndex
                FROM IF-MIB
        VlanIndex
                FROM CISCO-VTP-MIB
        eltMesMng
                FROM ELTEX-MES;

eltMesMacNotificationMIB MODULE-IDENTITY
    LAST-UPDATED    "201511190000Z" -- November 19, 2015    
    ORGANIZATION    "Eltex Enterprise Co, Ltd."
    CONTACT-INFO
        "www.eltex.nsk.ru"
    DESCRIPTION
        "Configuration of MAC notification feature."
    REVISION   "201511050000Z"
    DESCRIPTION
        "Initial version of this MIB module."

    REVISION        "201511190000Z" -- November 19, 2015
    DESCRIPTION
        "Deprecate all objects in this module."
    ::= { eltMesMng 7 }


eltMesMacNotificationObjects OBJECT IDENTIFIER ::= { eltMesMacNotificationMIB 1 }

-- -------------------- --
-- eltMesMnFlappingObjects --
-- -------------------- --
eltMesMnFlappingObjects OBJECT IDENTIFIER ::= { eltMesMacNotificationObjects 1 }

eltMnFlappingFeatureEnabled  OBJECT-TYPE
    SYNTAX        TruthValue
    MAX-ACCESS    read-write
    STATUS        deprecated
    DESCRIPTION
        "Specifies whether the MAC Flapping notification feature is 
         currently running in the device.

         Setting this object to false(2) disables the MAC Flapping 
         notification feature globally.

         Setting this object to true(1) will start the MAC Flapping 
         notification feature running in the device."
    DEFVAL { true }
    ::= { eltMesMnFlappingObjects 1 }

eltMnFlappingNotificationsEnabled OBJECT-TYPE
     SYNTAX          TruthValue
     MAX-ACCESS      read-write
     STATUS          deprecated
     DESCRIPTION
         "Specifies whether eltMnFlappingNotification notifications
          will or will not be sent when a MAC flapping is detected by
          the MAC flapping notification feature.

          Setting this object to false(2) will not send the
          eltMnFlappingNotification notifications.
   
          Setting this object to true(1) will send the 
          eltMnFlappingNotification notifications."
    DEFVAL { true }
    ::= { eltMesMnFlappingObjects 2 }

eltMnFlappingAddress OBJECT-TYPE
     SYNTAX          MacAddress
     MAX-ACCESS      read-only
     STATUS          deprecated
     DESCRIPTION
         "Indicates the MAC address that is flapping between
          eltMnFlappingFirstPortId and eltMnFlappingSecondPortId on 
          eltMnFlappingVlanNumber. 

          This object is instantiated only when eltMnFlappingFeatureEnabled 
          value is set to true(1) and a MAC flapping is detected by the MAC 
          flapping notification feature."
    ::= { eltMesMnFlappingObjects 3 }

eltMnFlappingVlanNumber OBJECT-TYPE
     SYNTAX          VlanIndex
     MAX-ACCESS      read-only
     STATUS          deprecated
     DESCRIPTION
         "Indicates the VLAN on which the eltMnFlappingAddress is flapping
          between eltMnFlappingFirstPortId to eltMnFlappingSecondPortId.

          This object is instantiated only when eltMnFlappingFeatureEnabled 
          value is set to true(1) and a MAC flapping is detected by the MAC 
          flapping notification feature."
    ::= { eltMesMnFlappingObjects 4 }

eltMnFlappingFirstPortId OBJECT-TYPE
     SYNTAX          Integer32 (1..65535) 
     MAX-ACCESS      read-only
     STATUS          deprecated
     DESCRIPTION
         "The first value of dot1dBasePort for the bridge port on which 
          the eltMnFlappingAddress is flapping on eltMnFlappingVlanNumber.

          This object is instantiated only when eltMnFlappingFeatureEnabled 
          value is set to true(1) and a MAC flapping is detected by the MAC 
          flapping notification feature."
     REFERENCE
               "dot1dBasePort is defined in RFC1493."
    ::= { eltMesMnFlappingObjects 5 }

eltMnFlappingSecondPortId OBJECT-TYPE
     SYNTAX          Integer32 (1..65535)
     MAX-ACCESS      read-only
     STATUS          deprecated
     DESCRIPTION
         "The second value of dot1dBasePort for the bridge port on which 
          the eltMnFlappingAddress is flapping on eltMnFlappingVlanNumber.

          This object is instantiated only when eltMnFlappingFeatureEnabled 
          value is set to true(1) and a MAC flapping is detected by the MAC 
          flapping notification feature."
     REFERENCE
               "dot1dBasePort is defined in RFC1493."
    ::= { eltMesMnFlappingObjects 6 }

eltMnFlappingTime OBJECT-TYPE
     SYNTAX          TimeStamp
     MAX-ACCESS      read-only
     STATUS          deprecated
     DESCRIPTION
         "The value of sysUpTime when a eltMnFlappingAddress is flapping 
          between eltMnFlappingFirstPortId and eltMnFlappingSecondPortId.

          This object is instantiated only when eltMnFlappingFeatureEnabled 
          value is set to true(1) and a MAC flapping is detected by the MAC 
          flapping notification feature."
    ::= { eltMesMnFlappingObjects 7 }

-- -------------- --
-- Notifications  --
-- -------------- --
eltMesMnNotificationPrefix OBJECT IDENTIFIER ::= { eltMesMacNotificationMIB 2 }

eltMesMnNotifications OBJECT IDENTIFIER ::= { eltMesMnNotificationPrefix 0 }

eltMnFlappingNotification NOTIFICATION-TYPE
    OBJECTS { 
              eltMnFlappingAddress,
              eltMnFlappingVlanNumber,
              eltMnFlappingFirstPortId,
              eltMnFlappingSecondPortId,
              eltMnFlappingTime
            }
    STATUS  deprecated
    DESCRIPTION
        "This notification is generated when a MAC address is 
         flapping between two or more interfaces."
    ::= { eltMesMnNotifications 1 } 

END
