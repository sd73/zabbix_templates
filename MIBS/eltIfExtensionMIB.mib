ELTEX-MES-IF-EXTENSION-MIB DEFINITIONS ::= BEGIN

-- Title:      ELTEX MES Switch Interfaces Extension Private
-- Version:    1.0
-- Date:       21 Sep 2012
-- 21-Sep-2012 - Added eltIfDot1qCustomEtherTypeEgressTable

IMPORTS
    eltMesIfExtensionMIB                                    FROM ELTEX-MES-MNG-MIB
    ifIndex, InterfaceIndex, InterfaceIndexOrZero           FROM IF-MIB
    PortList                                                FROM Q-BRIDGE-MIB
    Unsigned32, Integer32, Counter32,
    MODULE-IDENTITY, OBJECT-TYPE                            FROM SNMPv2-SMI
    Counter                                                 FROM RFC1155-SMI
    RowStatus                                               FROM SNMPv2-TC;

eltMesIfExtensionMIBObjects OBJECT IDENTIFIER ::= { eltMesIfExtensionMIB 1  }

eltMesIfExtDot1qCustomEtherType OBJECT IDENTIFIER ::= { eltMesIfExtensionMIBObjects 3  }
eltMesIfExtDot1q                OBJECT IDENTIFIER ::= { eltMesIfExtensionMIBObjects 4  }


eltIfDot1qCustomEgressEtherTypeTable OBJECT-TYPE
    SYNTAX          SEQUENCE OF EltIfDot1qCustomEgressEtherTypeEntry
    MAX-ACCESS      not-accessible
    STATUS          current
    DESCRIPTION        "A list of the interfaces that support
                        the 802.1q custom egress ethertype feature."
    ::= { eltMesIfExtDot1qCustomEtherType 1 }

eltIfDot1qCustomEgressEtherTypeEntry OBJECT-TYPE
    SYNTAX          EltIfDot1qCustomEgressEtherTypeEntry
    MAX-ACCESS      not-accessible
    STATUS          current
    DESCRIPTION        "An entry containing the custom egress EtherType
                        information for the interface.
                        Only interfaces with custom 802.1q
                        ethertype control are listed in the
                        table."
    INDEX           { ifIndex }
    ::= { eltIfDot1qCustomEgressEtherTypeTable 1 }

EltIfDot1qCustomEgressEtherTypeEntry ::= SEQUENCE {
	eltIfDot1qCustomEgressEtherType Integer32
}

eltIfDot1qCustomEgressEtherType OBJECT-TYPE
    SYNTAX          Integer32 (0..65535 )
    MAX-ACCESS      read-write
    STATUS          current
    DESCRIPTION        "The Dot1qEtherType allow administrator
                        to select a non-standard (other than 0x8100)
                        2-byte ethertype for the interface to
                        interoperate with third party vendor's system
                        that do not use the standard 0x8100 ethertype
                        to identify 802.1q-tagged frames.

                        The current administrative value of the
                        802.1q ethertype for the interface.  The
                        administrative 802.1q ethertype value may
                        differ from the operational 802.1q ethertype
                        value.  On some platforms, 802.1q ethertype
                        may be assigned per group rather than per port.
                        If multiple ports belong to a port group,
                        the 802.1q ethertype assigned to any of
                        the ports in such group will apply to all
                        ports in the same group.

                        To configure non-standard dot1q egress ethertype
                        is only recommended when the Eltex device
                        is connected to any third party vendor device."
    ::= { eltIfDot1qCustomEgressEtherTypeEntry 1 }

eltIfDot1qCustomIngressEtherTypeTable OBJECT-TYPE
    SYNTAX          SEQUENCE OF EltIfDot1qCustomIngressEtherTypeEntry
    MAX-ACCESS      not-accessible
    STATUS          current
    DESCRIPTION        "A list of the interfaces that support
                        the 802.1q custom ingress ethertype feature."
    ::= { eltMesIfExtDot1qCustomEtherType 2 }

eltIfDot1qCustomIngressEtherTypeEntry OBJECT-TYPE
    SYNTAX          EltIfDot1qCustomIngressEtherTypeEntry
    MAX-ACCESS      not-accessible
    STATUS          current
    DESCRIPTION        "An entry containing the custom ingress EtherTypes
                        set for the interface to classify stag and ctag.
                        Only interfaces with custom 802.1q
                        ethertype control are listed in the
                        table."
    INDEX           { ifIndex }
    ::= { eltIfDot1qCustomIngressEtherTypeTable 1 }

EltIfDot1qCustomIngressEtherTypeEntry ::= SEQUENCE {
	eltIfDot1qCustomIngressEtherType1 Integer32,
    eltIfDot1qCustomIngressEtherType2 Integer32,
    eltIfDot1qCustomIngressEtherType3 Integer32,
    eltIfDot1qCustomIngressEtherType4 Integer32,
    eltIfDot1qCustomIngressEtherType5 Integer32,
    eltIfDot1qCustomIngressEtherType6 Integer32,
    eltIfDot1qCustomIngressEtherType7 Integer32
}

eltIfDot1qCustomIngressEtherType1 OBJECT-TYPE
    SYNTAX          Integer32 (0 | 33024 )
    MAX-ACCESS      read-write
    STATUS          current
	DESCRIPTION     "This fields holds default ethertype 0x8100 or zero
					if ethertype 0x8100 is not used to classify SVLAN on
                    current interface."
    DEFVAL          { 33024 }
    ::= { eltIfDot1qCustomIngressEtherTypeEntry 1 }

eltIfDot1qCustomIngressEtherType2 OBJECT-TYPE
    SYNTAX          Integer32 (0..33023 |  33025..65535)
    MAX-ACCESS      read-write
    STATUS          current
	DESCRIPTION     "The custom ethertype to classify ingress vlan tags (SVLAN)
    				for the interface to interoperate with third party vendor's
                    system that do not use the standard 0x8100 ethertype
                    to identify 802.1q-tagged frames."
    DEFVAL          { 0 }
    ::= { eltIfDot1qCustomIngressEtherTypeEntry 2 }

eltIfDot1qCustomIngressEtherType3 OBJECT-TYPE
    SYNTAX          Integer32 (0..33023 |  33025..65535)
    MAX-ACCESS      read-write
    STATUS          current
	DESCRIPTION     "The custom ethertype to classify ingress vlan tags (SVLAN)
    				for the interface to interoperate with third party vendor's
                    system that do not use the standard 0x8100 ethertype
                    to identify 802.1q-tagged frames."
    DEFVAL          { 0 }
    ::= { eltIfDot1qCustomIngressEtherTypeEntry 3 }

eltIfDot1qCustomIngressEtherType4 OBJECT-TYPE
    SYNTAX          Integer32 (0..33023 |  33025..65535)
    MAX-ACCESS      read-write
    STATUS          current
	DESCRIPTION     "The custom ethertype to classify ingress vlan tags (SVLAN)
    				for the interface to interoperate with third party vendor's
                    system that do not use the standard 0x8100 ethertype
                    to identify 802.1q-tagged frames."
    DEFVAL          { 0 }
    ::= { eltIfDot1qCustomIngressEtherTypeEntry 4 }

eltIfDot1qCustomIngressEtherType5 OBJECT-TYPE
    SYNTAX          Integer32 (0..33023 |  33025..65535)
    MAX-ACCESS      read-write
    STATUS          current
	DESCRIPTION     "The custom ethertype to classify ingress vlan tags (SVLAN)
    				for the interface to interoperate with third party vendor's
                    system that do not use the standard 0x8100 ethertype
                    to identify 802.1q-tagged frames."
    DEFVAL          { 0 }
    ::= { eltIfDot1qCustomIngressEtherTypeEntry 5 }

eltIfDot1qCustomIngressEtherType6 OBJECT-TYPE
    SYNTAX          Integer32 (0..33023 |  33025..65535)
    MAX-ACCESS      read-write
    STATUS          current
	DESCRIPTION     "The custom ethertype to classify ingress vlan tags (SVLAN)
    				for the interface to interoperate with third party vendor's
                    system that do not use the standard 0x8100 ethertype
                    to identify 802.1q-tagged frames."
    DEFVAL          { 0 }
    ::= { eltIfDot1qCustomIngressEtherTypeEntry 6 }

eltIfDot1qCustomIngressEtherType7 OBJECT-TYPE
    SYNTAX          Integer32 (0..33023 |  33025..65535)
    MAX-ACCESS      read-write
    STATUS          current
	DESCRIPTION     "The custom ethertype to classify ingress vlan tags (SVLAN)
    				for the interface to interoperate with third party vendor's
                    system that do not use the standard 0x8100 ethertype
                    to identify 802.1q-tagged frames."
    DEFVAL          { 0 }
    ::= { eltIfDot1qCustomIngressEtherTypeEntry 7 }


eltIfDot1qIngressCvlanTable OBJECT-TYPE
    SYNTAX          SEQUENCE OF EltIfDot1qIngressCvlanEntry
    MAX-ACCESS      not-accessible
    STATUS          current
    DESCRIPTION     "A list of the interfaces ingress C-VLAN settings."
    ::= { eltMesIfExtDot1q 1 }

eltIfDot1qIngressCvlanEntry OBJECT-TYPE
    SYNTAX          EltIfDot1qIngressCvlanEntry
    MAX-ACCESS      not-accessible
    STATUS          current
    DESCRIPTION     "An entry containing ingress C-VLAN assignment
                     for the interface."
    INDEX           { ifIndex }
    ::= { eltIfDot1qIngressCvlanTable 1 }

EltIfDot1qIngressCvlanEntry ::= SEQUENCE {
        eltIfDot1qIngressCvlanTag Integer32
}

eltIfDot1qIngressCvlanTag OBJECT-TYPE
    SYNTAX          Integer32 (0..4095 )
    MAX-ACCESS      read-write
    STATUS          current
    DESCRIPTION     "C-VLAN tag for the interface assigned
                     in ingress pipe. 0 means no C-VLAN assignment."
    ::= { eltIfDot1qIngressCvlanEntry 1 }

END
