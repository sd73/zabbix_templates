ELT-MES-DEV-PARAMS DEFINITIONS ::= BEGIN

-- Title:      Eltex's MES Switches Private MIB
-- Version:    2.00
-- Date:       16-Sep-2015
--

IMPORTS
    MODULE-IDENTITY, OBJECT-TYPE    FROM SNMPv2-SMI
    DisplayString                   FROM SNMPv2-TC
    eltMes                          FROM ELTEX-MES
    rndImageInfoEntry               FROM RADLAN-DEVICEPARAMS-MIB
    ;

eltMesDevParams MODULE-IDENTITY
                LAST-UPDATED "201212140000Z"
                ORGANIZATION "Eltex Enterprise Co, Ltd."
                CONTACT-INFO
                      "www.eltex.nsk.ru"
                DESCRIPTION
                      "This private MIB module defines Eltex's device parameters MIBs."
                REVISION "201509160000Z"
                DESCRIPTION
                      "Added eltImageInfoTable."
                REVISION "201212140000Z"
                DESCRIPTION
                      "Initial revision."
        ::= { eltMes 2 }

eltMesBootPassword OBJECT IDENTIFIER ::= { eltMesDevParams 17 }
-- see eltBootPassword.mib

--
-- eltImageInfoTable
--

eltImageInfoTable OBJECT-TYPE
    SYNTAX      SEQUENCE OF EltImageInfoEntry
    MAX-ACCESS  not-accessible
    STATUS      current
    DESCRIPTION
        "The table contains information about images"
    ::= { eltMesDevParams 18 }

eltImageInfoEntry OBJECT-TYPE
    SYNTAX      EltImageInfoEntry
    MAX-ACCESS  not-accessible
    STATUS      current
    DESCRIPTION
        "This table augments existing RADLAN table rndImageInfoTable"
    AUGMENTS { rndImageInfoEntry }
    ::= { eltImageInfoTable 1 }

EltImageInfoEntry ::= SEQUENCE {
    eltImage1CommitHash  DisplayString,
    eltImage2CommitHash  DisplayString,
    eltImage1BuildTag    DisplayString,
    eltImage2BuildTag    DisplayString,
    eltImage1BuildNumber DisplayString,
    eltImage2BuildNumber DisplayString
}

eltImage1CommitHash OBJECT-TYPE
       SYNTAX      DisplayString
       MAX-ACCESS  read-only
       STATUS      current
       DESCRIPTION "Hash commit of image-1."
       ::= { eltImageInfoEntry 1 }

eltImage2CommitHash OBJECT-TYPE
       SYNTAX      DisplayString
       MAX-ACCESS  read-only
       STATUS      current
       DESCRIPTION "Hash commit of image-2."
       ::= { eltImageInfoEntry 2 }
       
eltImage1BuildTag OBJECT-TYPE
       SYNTAX      DisplayString
       MAX-ACCESS  read-only
       STATUS      current
       DESCRIPTION "Build branch of image-1."
       ::= { eltImageInfoEntry 3 }

eltImage2BuildTag OBJECT-TYPE
       SYNTAX      DisplayString
       MAX-ACCESS  read-only
       STATUS      current
       DESCRIPTION "Build branch of image-2."
       ::= { eltImageInfoEntry 4 }

eltImage1BuildNumber OBJECT-TYPE
       SYNTAX      DisplayString
       MAX-ACCESS  read-only
       STATUS      current
       DESCRIPTION "Build describe number of image-1."
       ::= { eltImageInfoEntry 5 }

eltImage2BuildNumber OBJECT-TYPE
       SYNTAX      DisplayString
       MAX-ACCESS  read-only
       STATUS      current
       DESCRIPTION "Build describe number of image-2."
       ::= { eltImageInfoEntry 6 }
       

END
