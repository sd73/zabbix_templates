ELTEX-MES-MIB-OBJECTS DEFINITIONS ::= BEGIN

IMPORTS
    eltMesIfMIBObjects              FROM ELTEX-MES-IF-MIB
    MODULE-IDENTITY, OBJECT-TYPE,
    Integer32                       FROM SNMPv2-SMI
    DisplayString, TruthValue       FROM SNMPv2-TC
    ifEntry                         FROM IF-MIB;

eltIfExtTable OBJECT-TYPE
    SYNTAX      SEQUENCE OF EltIfExtEntry
    MAX-ACCESS  not-accessible
    STATUS      current
    DESCRIPTION
        ""
    ::= { eltMesIfMIBObjects 1 }

eltIfExtEntry OBJECT-TYPE
    SYNTAX      EltIfExtEntry
    MAX-ACCESS  not-accessible
    STATUS      current
    DESCRIPTION
        ""
    AUGMENTS { ifEntry }
    ::= { eltIfExtTable 1 }

EltIfExtEntry ::= SEQUENCE {
    eltIfLongDescr    DisplayString,
    eltIfAdminMtu     Integer32
}

eltIfLongDescr   OBJECT-TYPE
    SYNTAX      DisplayString (SIZE(0..160))
    MAX-ACCESS  read-write
    STATUS      current
    DESCRIPTION
    "Indicates description for an interface.
     Difference between ifAlies and LongDescr is
     in the number of characters used to describe
     a specific interface"
    ::= { eltIfExtEntry 1 }

eltIfAdminMtu OBJECT-TYPE
    SYNTAX          Integer32 (0 | 128..9000)
    MAX-ACCESS      read-write
    STATUS          current
    DESCRIPTION
        "The MTU configured by the administrator.
        This object is exactly same as 'ifMtu' in
        ifTable from IF-MIB for the same ifIndex
        value, except that it is configurable by the
        administrator. Zero value means using global
        configuration for this interface (depends on
        Jumbo frame enabled). For more description of
        this object refer to 'ifMtu' in IF-MIB."
	DEFVAL { 0 }
    ::= { eltIfExtEntry 2 }

eltIfUpDownTrapEnable OBJECT-TYPE
    SYNTAX         INTEGER { enabled(1), disabled(2) }
    MAX-ACCESS     read-write
    STATUS         current
    DESCRIPTION
        "Indicates whether linkUp/linkDown traps should be
        generated by system."
    ::= { eltMesIfMIBObjects 7 }

END
