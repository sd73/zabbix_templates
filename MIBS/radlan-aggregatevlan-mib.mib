RADLAN-AGGREGATEVLAN-MIB DEFINITIONS ::= BEGIN

-- Title:                RADLAN ROS
--                       Private AGGREGATE VLAN MIB
-- Version:              7.46
-- Date:                 14-Jan-2007

IMPORTS
    rnd                                                     FROM RADLAN-MIB
    OBJECT-TYPE, MODULE-IDENTITY                            FROM SNMPv2-SMI
    DisplayString, RowStatus                                FROM SNMPv2-TC
    InterfaceIndex                                          FROM IF-MIB;

rlAggregateVlan MODULE-IDENTITY
                LAST-UPDATED "200701020000Z"
                ORGANIZATION "Marvell Semiconductor, Inc."
                CONTACT-INFO
					"5488 Marvell Lane
					Santa Clara, CA 95054
					USA

					Website:  www.marvell.com"
                DESCRIPTION
                      "This private MIB module defines Aggregate Vlan private MIBs."
                REVISION "200701020000Z"
                DESCRIPTION
                      "Initial revision."
        ::= { rnd 73 }

rlAggregateVlanMibVersion OBJECT-TYPE
    SYNTAX      INTEGER
    MAX-ACCESS      read-only
    STATUS      current
    DESCRIPTION
        "MIB's version, the current version is 1."
::= { rlAggregateVlan 1 }

rlAggregateVlanTable OBJECT-TYPE
    SYNTAX  SEQUENCE OF RlAggregateVlanEntry
    MAX-ACCESS  not-accessible
    STATUS  current
    DESCRIPTION
        "The table creates an aggregateVlans, the IfIndex is from 10000"
    ::= { rlAggregateVlan 2 }

rlAggregateVlanEntry OBJECT-TYPE
    SYNTAX  RlAggregateVlanEntry
    MAX-ACCESS  not-accessible
    STATUS  current
    DESCRIPTION
        "The row definition for this table."
    INDEX { rlAggregateVlanIndex }
    ::= { rlAggregateVlanTable 1 }

RlAggregateVlanEntry ::= SEQUENCE {
    rlAggregateVlanIndex        InterfaceIndex,
    rlAggregateVlanName         DisplayString,
    rlAggregateVlanPhysAddressType  INTEGER,
    rlAggregateVlanStatus       RowStatus
}

rlAggregateVlanIndex OBJECT-TYPE
    SYNTAX  InterfaceIndex
    MAX-ACCESS  not-accessible
    STATUS  current
    DESCRIPTION
        "This index indicate the aggrigateVlan id, the aggregate
        vlan index is starting from 10000 "
    ::= { rlAggregateVlanEntry 1 }

rlAggregateVlanName OBJECT-TYPE
    SYNTAX  DisplayString (SIZE(0..32))
    MAX-ACCESS  read-create
    STATUS  current
    DESCRIPTION
        "The name of the aggregateVlan "
    DEFVAL {""}
    ::= { rlAggregateVlanEntry 2 }

rlAggregateVlanPhysAddressType OBJECT-TYPE
   SYNTAX  INTEGER {
        default(1),
        reserve(2)
   }
   MAX-ACCESS   read-create
   STATUS   current
   DESCRIPTION
        " This variable indicates whether the physical address assigned to this
          VLAN should be the default one or be chosen from the set of
          reserved physical addresses of the device."
   DEFVAL{default}
   ::=  { rlAggregateVlanEntry 3}

rlAggregateVlanStatus OBJECT-TYPE
    SYNTAX  RowStatus
    MAX-ACCESS  read-create
    STATUS  current
    DESCRIPTION
        "The status of the aggregateVlan table entry. It's used to delete an entry"
    ::= { rlAggregateVlanEntry 4}

rlAggregateSubVlanTable OBJECT-TYPE
    SYNTAX  SEQUENCE OF RlAggregateSubVlanEntry
    MAX-ACCESS  not-accessible
    STATUS  current
    DESCRIPTION
        "The table indicates all the allocated sub-vlans to the
        aggregateVlans, an entry in the rlAggregateVlanTable must
        be exist before allocating the subVlans"
    ::= { rlAggregateVlan 3 }

rlAggregateSubVlanEntry OBJECT-TYPE
    SYNTAX  RlAggregateSubVlanEntry
    MAX-ACCESS  not-accessible
    STATUS  current
    DESCRIPTION
        "The row definition for this table."
    INDEX { rlAggregateVlanIndex, rlAggregateSubVlanIfIndex }
    ::= { rlAggregateSubVlanTable 1 }

RlAggregateSubVlanEntry ::= SEQUENCE {
    rlAggregateSubVlanIfIndex   InterfaceIndex,
    rlAggregateSubVlanStatus    RowStatus
}

rlAggregateSubVlanIfIndex OBJECT-TYPE
    SYNTAX  InterfaceIndex
    MAX-ACCESS  read-only
    STATUS  current
    DESCRIPTION
        "Indicate the subVlan that allocated to the aggregate vlan"
    ::= { rlAggregateSubVlanEntry 1}

rlAggregateSubVlanStatus OBJECT-TYPE
    SYNTAX  RowStatus
    MAX-ACCESS  read-create
    STATUS  current
    DESCRIPTION
        "The status of the aggregateSubVlan table entry.
        It's used to delete an entry"
    ::= { rlAggregateSubVlanEntry 2}

rlAggregateVlanArpProxy OBJECT-TYPE
    SYNTAX INTEGER {
       enable(1),
       disable(2)
    }
    MAX-ACCESS read-write
    STATUS current
    DESCRIPTION
         "When ARP Proxy is enabled, the router can respond to
          ARP requests for nodes located on different sub-vlans,
          which belong to the same Super VLAN.The router responds
          with its own MAC address.
          When ARP Proxy is disabled, the router responds only
          to ARP requests for its own IP addresses."
    DEFVAL  { disable }
    ::= { rlAggregateVlan 4 }

END
