ELTEX-MES-QOS-CLI-MIB DEFINITIONS ::= BEGIN

-- Title:      Eltex MES QoS Configuration
-- Version:    1.2
-- Date:       7-Jun-2021
--
-- 05-Aug-2015 Added eltQosClassMapActionCfgTable
-- 28-Jan-2016 Added eltQosDscpToCosTable
-- 28-Dec-2016 Added eltQosCosToDscpTable

IMPORTS
    MODULE-IDENTITY, OBJECT-TYPE, Unsigned32    FROM SNMPv2-SMI
    RowStatus, TruthValue                       FROM SNMPv2-TC
    rlQosPolicerEntry,
    rlQosIfPolicyEntry,rlQosAceTidxEntry,
    ClassMapAction,rlQosClassMapIndex           FROM RADLAN-QOS-CLI-MIB
    eltMesQosCliMib                             FROM ELTEX-MES;

EltQosIfTrustMode ::= TEXTUAL-CONVENTION
    STATUS  current
    DESCRIPTION
        "Specifies one of 4 QoS trust mode for port:
        none    - Do not classify ingress packets with the packet CoS/DSCP values.
        cos     - Classifies ingress packets with the packet CoS values.
                  For untagged packets, the port default CoS is used.
        dscp    - Classifies ingress packets with the packet DSCP values.
        cos-dscp- Classifies ingress packets with the packet DSCP values.
                  For non-ip tagged packets, classifies ingress packets with
                  the packet CoS values."
    SYNTAX  INTEGER {
        none(0),
        cos(1),
        dscp(2),
        cos-dscp(3)
}

EltQosMappingType ::= TEXTUAL-CONVENTION
    STATUS  current
    DESCRIPTION
        "Specifies available mapping type:
         cos-dscp - convert ingress packets the CoS values to the DSCP values
         dscp-cos - convert ingress packets the DSCP values to the CoS values"
    SYNTAX  INTEGER {
        cos-dscp(0),
        dscp-cos(1)
}

EltQosTrafficLimiterMode  ::= TEXTUAL-CONVENTION
    STATUS current
    DESCRIPTION    "Types of traffic measurement in kbps or pps."
    SYNTAX INTEGER {
       kbps(0),
       pps(1)
}

EltPolicerAction ::= TEXTUAL-CONVENTION
    STATUS  current
    DESCRIPTION
        "Specifies one of 3 Policer Action:
         1- No Action
         2- Drop out of profile packets.
         3- Remark out of profile packets."
    SYNTAX  INTEGER {
        none(1),
        drop(2),
        remark(3)
}

--------------------------------------------------------------------------------
-- eltQosOffsetListTable
--------------------------------------------------------------------------------

eltQosOffsetListTable OBJECT-TYPE
    SYNTAX SEQUENCE OF EltQosOffsetListEntry
    MAX-ACCESS not-accessible
    STATUS current
    DESCRIPTION
        "This table specifies Offset List Table information"
    ::= { eltMesQosCliMib 1 }

eltQosOffsetListEntry OBJECT-TYPE
    SYNTAX     EltQosOffsetListEntry
    MAX-ACCESS not-accessible
    STATUS     current
    DESCRIPTION
        "Each entry in this table describes one Offset List.
        The information includes: Offset List name and the offsets pointers.
        The index is an octet string name"
    INDEX { eltQosAclIndex,
            eltQosOffsetListName }
    ::= { eltQosOffsetListTable 1 }

EltQosOffsetListEntry ::= SEQUENCE {
    eltQosAclIndex                  INTEGER,
    eltQosOffsetListName            OCTET STRING,
    eltQosOffsetListOffsetPointer1  INTEGER,
    eltQosOffsetListOffsetPointer2  INTEGER,
    eltQosOffsetListOffsetPointer3  INTEGER,
    eltQosOffsetListOffsetPointer4  INTEGER,
    eltQosOffsetListOffsetPointer5  INTEGER,
    eltQosOffsetListStatus          RowStatus,
    eltQosOffsetListOffsetPointer6  INTEGER,
    eltQosOffsetListOffsetPointer7  INTEGER,
    eltQosOffsetListOffsetPointer8  INTEGER,
    eltQosOffsetListOffsetPointer9  INTEGER,
    eltQosOffsetListOffsetPointer10 INTEGER,
    eltQosOffsetListOffsetPointer11 INTEGER,
    eltQosOffsetListOffsetPointer12 INTEGER,
    eltQosOffsetListOffsetPointer13 INTEGER
    }

eltQosAclIndex OBJECT-TYPE
    SYNTAX     INTEGER
    MAX-ACCESS read-create
    STATUS     current
    DESCRIPTION
        "An arbitrary incremental Index
         for the ACL offset list connection."
    ::= { eltQosOffsetListEntry 1 }

eltQosOffsetListName OBJECT-TYPE
    SYNTAX     OCTET STRING(SIZE(0..32))
    MAX-ACCESS not-accessible
    STATUS     current
    DESCRIPTION
        "Offset list name."
    ::= { eltQosOffsetListEntry 2 }

eltQosOffsetListOffsetPointer1 OBJECT-TYPE
    SYNTAX     INTEGER
    MAX-ACCESS read-create
    STATUS     current
    DESCRIPTION
        "Offset pointer is an index of table rlQosOffsetTable."
    ::= { eltQosOffsetListEntry 3 }

eltQosOffsetListOffsetPointer2 OBJECT-TYPE
    SYNTAX     INTEGER
    MAX-ACCESS read-create
    STATUS     current
    DESCRIPTION
        "Offset pointer is an index of table rlQosOffsetTable."
    ::= { eltQosOffsetListEntry 4 }

eltQosOffsetListOffsetPointer3 OBJECT-TYPE
    SYNTAX     INTEGER
    MAX-ACCESS read-create
    STATUS     current
    DESCRIPTION
        "Offset pointer is an index of table rlQosOffsetTable."
    ::= { eltQosOffsetListEntry 5}

eltQosOffsetListOffsetPointer4 OBJECT-TYPE
    SYNTAX     INTEGER
    MAX-ACCESS read-create
    STATUS     current
    DESCRIPTION
        "Offset pointer is an index of table rlQosOffsetTable."
    ::= { eltQosOffsetListEntry 6}

eltQosOffsetListOffsetPointer5 OBJECT-TYPE
    SYNTAX     INTEGER
    MAX-ACCESS read-create
    STATUS     current
    DESCRIPTION
        "Offset pointer is an index of table rlQosOffsetTable."
    ::= { eltQosOffsetListEntry 7 }

eltQosOffsetListStatus OBJECT-TYPE
    SYNTAX      RowStatus
    MAX-ACCESS  read-create
    STATUS      current
    DESCRIPTION
       "The status of a table entry.
        It is used to delete/Add an entry from this table."
    ::= { eltQosOffsetListEntry 8 }

eltQosOffsetListOffsetPointer6 OBJECT-TYPE
    SYNTAX     INTEGER
    MAX-ACCESS read-create
    STATUS     current
    DESCRIPTION
        "Offset pointer is an index of table eltQosOffsetTable."
    ::= { eltQosOffsetListEntry 9 }

eltQosOffsetListOffsetPointer7 OBJECT-TYPE
    SYNTAX     INTEGER
    MAX-ACCESS read-create
    STATUS     current
    DESCRIPTION
        "Offset pointer is an index of table eltQosOffsetTable."
    ::= { eltQosOffsetListEntry 10 }

eltQosOffsetListOffsetPointer8 OBJECT-TYPE
    SYNTAX     INTEGER
    MAX-ACCESS read-create
    STATUS     current
    DESCRIPTION
        "Offset pointer is an index of table eltQosOffsetTable."
    ::= { eltQosOffsetListEntry 11 }

eltQosOffsetListOffsetPointer9 OBJECT-TYPE
    SYNTAX     INTEGER
    MAX-ACCESS read-create
    STATUS     current
    DESCRIPTION
        "Offset pointer is an index of table eltQosOffsetTable."
    ::= { eltQosOffsetListEntry 12 }

eltQosOffsetListOffsetPointer10 OBJECT-TYPE
    SYNTAX     INTEGER
    MAX-ACCESS read-create
    STATUS     current
    DESCRIPTION
        "Offset pointer is an index of table eltQosOffsetTable."
    ::= { eltQosOffsetListEntry 13 }

eltQosOffsetListOffsetPointer11 OBJECT-TYPE
    SYNTAX     INTEGER
    MAX-ACCESS read-create
    STATUS     current
    DESCRIPTION
        "Offset pointer is an index of table eltQosOffsetTable."
    ::= { eltQosOffsetListEntry 14 }

eltQosOffsetListOffsetPointer12 OBJECT-TYPE
    SYNTAX     INTEGER
    MAX-ACCESS read-create
    STATUS     current
    DESCRIPTION
        "Offset pointer is an index of table eltQosOffsetTable."
    ::= { eltQosOffsetListEntry 15 }

eltQosOffsetListOffsetPointer13 OBJECT-TYPE
    SYNTAX     INTEGER
    MAX-ACCESS read-create
    STATUS     current
    DESCRIPTION
        "Offset pointer is an index of table eltQosOffsetTable."
    ::= { eltQosOffsetListEntry 16 }

--------------------------------------------------------------------------------
-- eltQosAceTidxTable
--------------------------------------------------------------------------------

eltQosAceTidxTable OBJECT-TYPE
    SYNTAX SEQUENCE OF EltQosAceTidxEntry
    MAX-ACCESS not-accessible
    STATUS current
    DESCRIPTION
       "This table specifies ACE table with two index information."
    ::= { eltMesQosCliMib 10 }

eltQosAceTidxEntry OBJECT-TYPE
    SYNTAX  EltQosAceTidxEntry
    MAX-ACCESS  not-accessible
    STATUS  current
    DESCRIPTION
        "Augments rlQosAceTidxEntry to add more tuples."
    AUGMENTS { rlQosAceTidxEntry }
    ::= { eltQosAceTidxTable 1 }

EltQosAceTidxEntry ::= SEQUENCE {
    eltQosAceTidxTuple1   INTEGER,
    eltQosAceTidxTuple2   INTEGER,
    eltQosAceTidxTuple3   INTEGER,
    eltQosAceTidxTuple4   INTEGER,
    eltQosAceTidxTuple5   INTEGER,
    eltQosAceTidxTuple6   INTEGER,
    eltQosAceTidxTuple7   INTEGER,
    eltQosAceTidxTuple8   INTEGER,
    eltQosAceTidxTuple9   INTEGER,
    eltQosAceTidxTuple10  INTEGER,
    eltQosAceTidxTuple11  INTEGER,
    eltQosAceTidxTuple12  INTEGER,
    eltQosAceTidxTuple13  INTEGER,
    eltQosAceTidxTuple14  INTEGER,
    eltQosAceTidxTuple15  INTEGER
}

eltQosAceTidxTuple1 OBJECT-TYPE
    SYNTAX INTEGER
    MAX-ACCESS read-create
    STATUS current
    DESCRIPTION
        "ACE Tuple pointer."
    ::= { eltQosAceTidxEntry 1 }

eltQosAceTidxTuple2 OBJECT-TYPE
    SYNTAX INTEGER
    MAX-ACCESS read-create
    STATUS current
    DESCRIPTION
        "ACE Tuple pointer."
    ::= { eltQosAceTidxEntry 2 }

eltQosAceTidxTuple3 OBJECT-TYPE
    SYNTAX INTEGER
    MAX-ACCESS read-create
    STATUS current
    DESCRIPTION
        "ACE Tuple pointer."
    ::= { eltQosAceTidxEntry 3 }

eltQosAceTidxTuple4 OBJECT-TYPE
    SYNTAX INTEGER
    MAX-ACCESS read-create
    STATUS current
    DESCRIPTION
        "ACE Tuple pointer."
    ::= { eltQosAceTidxEntry 4 }

eltQosAceTidxTuple5 OBJECT-TYPE
    SYNTAX INTEGER
    MAX-ACCESS read-create
    STATUS current
    DESCRIPTION
        "ACE Tuple pointer."
    ::= { eltQosAceTidxEntry 5 }

eltQosAceTidxTuple6 OBJECT-TYPE
    SYNTAX INTEGER
    MAX-ACCESS read-create
    STATUS current
    DESCRIPTION
        "ACE Tuple pointer."
    ::= { eltQosAceTidxEntry 6 }

eltQosAceTidxTuple7 OBJECT-TYPE
    SYNTAX INTEGER
    MAX-ACCESS read-create
    STATUS current
    DESCRIPTION
        "ACE Tuple pointer."
    ::= { eltQosAceTidxEntry 7 }

eltQosAceTidxTuple8 OBJECT-TYPE
    SYNTAX INTEGER
    MAX-ACCESS read-create
    STATUS current
    DESCRIPTION
        "ACE Tuple pointer."
    ::= { eltQosAceTidxEntry 8 }

eltQosAceTidxTuple9 OBJECT-TYPE
    SYNTAX INTEGER
    MAX-ACCESS read-create
    STATUS current
    DESCRIPTION
        "ACE Tuple pointer."
    ::= { eltQosAceTidxEntry 9 }

eltQosAceTidxTuple10 OBJECT-TYPE
    SYNTAX INTEGER
    MAX-ACCESS read-create
    STATUS current
    DESCRIPTION
        "ACE Tuple pointer."
    ::= { eltQosAceTidxEntry 10 }

eltQosAceTidxTuple11 OBJECT-TYPE
    SYNTAX INTEGER
    MAX-ACCESS read-create
    STATUS current
    DESCRIPTION
        "ACE Tuple pointer."
    ::= { eltQosAceTidxEntry 11 }

eltQosAceTidxTuple12 OBJECT-TYPE
    SYNTAX INTEGER
    MAX-ACCESS read-create
    STATUS current
    DESCRIPTION
        "ACE Tuple pointer."
    ::= { eltQosAceTidxEntry 12 }

eltQosAceTidxTuple13 OBJECT-TYPE
    SYNTAX INTEGER
    MAX-ACCESS read-create
    STATUS current
    DESCRIPTION
        "ACE Tuple pointer."
    ::= { eltQosAceTidxEntry 13 }

eltQosAceTidxTuple14 OBJECT-TYPE
    SYNTAX INTEGER
    MAX-ACCESS read-create
    STATUS current
    DESCRIPTION
        "ACE Tuple pointer."
    ::= { eltQosAceTidxEntry 14 }

eltQosAceTidxTuple15 OBJECT-TYPE
    SYNTAX INTEGER
    MAX-ACCESS read-create
    STATUS current
    DESCRIPTION
        "ACE Tuple pointer."
    ::= { eltQosAceTidxEntry 15 }

--------------------------------------------------------------------------------
-- eltQosClassMapActionCfgTable
--------------------------------------------------------------------------------

eltQosClassMapActionCfgTable OBJECT-TYPE
    SYNTAX SEQUENCE OF EltQosClassMapActionCfgEntry
    MAX-ACCESS not-accessible
    STATUS current
    DESCRIPTION
        "This table specifes list of actions for each class in
         rlQosClassMapTable."
    ::= { eltMesQosCliMib 5 }

eltQosClassMapActionCfgEntry OBJECT-TYPE
    SYNTAX EltQosClassMapActionCfgEntry
    MAX-ACCESS not-accessible
    STATUS current
    DESCRIPTION
        "Each entry in this table describes configuration information about
         actions for one class.
         This table is a sub-table for rlQosClassMapTable."
    INDEX { rlQosClassMapIndex,
            eltQosClassMapActionCfgAction }
    ::= { eltQosClassMapActionCfgTable 1 }

EltQosClassMapActionCfgEntry ::= SEQUENCE {
    eltQosClassMapActionCfgAction  ClassMapAction,
    eltQosClassMapActionCfgValue   INTEGER,
    eltQosClassMapActionCfgStatus  RowStatus
}

eltQosClassMapActionCfgAction OBJECT-TYPE
    SYNTAX ClassMapAction
    MAX-ACCESS read-write
    STATUS current
    DESCRIPTION
        "Action to be taken when packet matches classification."
    ::= { eltQosClassMapActionCfgEntry 1 }

eltQosClassMapActionCfgValue OBJECT-TYPE
    SYNTAX INTEGER
    MAX-ACCESS read-write
    STATUS current
    DESCRIPTION
        "Value for the action described in eltQosClassMapActionCfgAction."
    ::= { eltQosClassMapActionCfgEntry 2 }

eltQosClassMapActionCfgStatus OBJECT-TYPE
    SYNTAX RowStatus
    MAX-ACCESS read-create
    STATUS current
    DESCRIPTION
       "The status of a table entry. It is used to add/delete an entry from this
        table."
    ::= { eltQosClassMapActionCfgEntry 3 }

--------------------------------------------------------------------------------
-- eltQosDscpToCosTable
--------------------------------------------------------------------------------

eltQosDscpToCosTable OBJECT-TYPE
    SYNTAX      SEQUENCE OF EltQosDscpToCosEntry
    MAX-ACCESS  not-accessible
    STATUS      current
    DESCRIPTION
        "This table specifies The DSCP
         To CoS mapping"
    ::= { eltMesQosCliMib 6 }

eltQosDscpToCosEntry OBJECT-TYPE
    SYNTAX      EltQosDscpToCosEntry
    MAX-ACCESS  not-accessible
    STATUS      current
    DESCRIPTION
        "Each entry in this table describes the new
         CoS for the packet.
         The index is DSCP represent by eltQosDscp."
    INDEX { eltQosDscp }
    ::= { eltQosDscpToCosTable 1 }

EltQosDscpToCosEntry ::= SEQUENCE {
    eltQosDscp  INTEGER,
    eltQosCos   INTEGER
}

eltQosDscp OBJECT-TYPE
    SYNTAX      INTEGER (0..63)
    MAX-ACCESS  not-accessible
    STATUS      current
    DESCRIPTION
        "DSCP value."
    ::= { eltQosDscpToCosEntry 1 }

eltQosCos OBJECT-TYPE
    SYNTAX      INTEGER (0..7)
    MAX-ACCESS  read-create
    STATUS      current
    DESCRIPTION
        "Re-mark CoS."
    ::= { eltQosDscpToCosEntry 2 }

--------------------------------------------------------------------------------
-- eltQosCosToDscpTable
--------------------------------------------------------------------------------

eltQosCosToDscpTable OBJECT-TYPE
    SYNTAX      SEQUENCE OF EltQosCosToDscpEntry
    MAX-ACCESS  not-accessible
    STATUS      current
    DESCRIPTION
        "This table specifies The CoS
         to DSCP mapping"
    ::= { eltMesQosCliMib 7 }

eltQosCosToDscpEntry OBJECT-TYPE
    SYNTAX      EltQosCosToDscpEntry
    MAX-ACCESS  not-accessible
    STATUS      current
    DESCRIPTION
        "Each entry in this table describes the new
         DSCP value for the packet.
         The index is CoS represent by eltQosDscp."
    INDEX { eltQosCosIndex }
    ::= { eltQosCosToDscpTable 1 }

EltQosCosToDscpEntry ::= SEQUENCE {
    eltQosCosIndex      INTEGER,
    eltQosDscpValue     INTEGER
}

eltQosCosIndex OBJECT-TYPE
    SYNTAX      INTEGER (0..7)
    MAX-ACCESS  not-accessible
    STATUS      current
    DESCRIPTION
        "CoS value."
    ::= { eltQosCosToDscpEntry 1 }

eltQosDscpValue OBJECT-TYPE
    SYNTAX      INTEGER (0..63)
    MAX-ACCESS  read-create
    STATUS      current
    DESCRIPTION
        "Re-mark DSCP."
    ::= { eltQosCosToDscpEntry 2 }

--------------------------------------------------------------------------------
-- eltQosIfConfigTable
--------------------------------------------------------------------------------

eltQosIfConfigTable OBJECT-TYPE
    SYNTAX      SEQUENCE OF EltQosIfConfigEntry
    MAX-ACCESS  not-accessible
    STATUS      current
    DESCRIPTION
        "Specifies The QoS trust mode for the interfaces in basic mode"
    ::= { eltMesQosCliMib 8 }

eltQosIfConfigEntry OBJECT-TYPE
    SYNTAX      EltQosIfConfigEntry
    MAX-ACCESS  not-accessible
    STATUS      current
    DESCRIPTION
        "Specifies The QoS trust mode for the interface in basic mode"
    AUGMENTS { rlQosIfPolicyEntry }
    ::= { eltQosIfConfigTable 1 }

EltQosIfConfigEntry ::= SEQUENCE {
    eltQosIfTrustMode                   EltQosIfTrustMode,
    eltQosIfCirPortRateLimitPps         Unsigned32,
    eltQosIfCbsPortRateLimitPackets     Unsigned32
}

eltQosIfTrustMode OBJECT-TYPE
    SYNTAX      EltQosIfTrustMode
    MAX-ACCESS  read-write
    STATUS      current
    DESCRIPTION
       "Defines the interface qos trust operation mode relevant for qos basic mode."
    ::= { eltQosIfConfigEntry 1 }

eltQosIfCirPortRateLimitPps OBJECT-TYPE
    SYNTAX      Unsigned32
    MAX-ACCESS  read-write
    STATUS      current
    DESCRIPTION
        "Block the flooding of packets when the value in pps specified is reached.
         Rate equal to 0 means that the rate limit does not apply to traffic."
    DEFVAL { 0 }
    ::= { eltQosIfConfigEntry 2 }

eltQosIfCbsPortRateLimitPackets OBJECT-TYPE
    SYNTAX      Unsigned32
    MAX-ACCESS  read-write
    STATUS      current
    DESCRIPTION
        "Committed burst in packets."
    DEFVAL { 0 }
    ::= { eltQosIfConfigEntry 3 }

--------------------------------------------------------------------------------
-- eltQosMappingCfgTable
--------------------------------------------------------------------------------

eltQosMappingCfgTable OBJECT-TYPE
    SYNTAX      SEQUENCE OF EltQosMappingCfgEntry
    MAX-ACCESS  not-accessible
    STATUS      current
    DESCRIPTION
        "This table responsible to set the global QoS mapping configuration."
    ::= { eltMesQosCliMib 9 }

eltQosMappingCfgEntry OBJECT-TYPE
    SYNTAX      EltQosMappingCfgEntry
    MAX-ACCESS  not-accessible
    STATUS      current
    DESCRIPTION
        "This table responsible to set the global QoS mapping configuration."
    INDEX { eltQosMappingCfgIndex }
    ::= { eltQosMappingCfgTable 1 }

EltQosMappingCfgEntry ::= SEQUENCE {
    eltQosMappingCfgIndex     EltQosMappingType,
    eltQosMappingCfgEnable    TruthValue
}

eltQosMappingCfgIndex OBJECT-TYPE
    SYNTAX      EltQosMappingType
    MAX-ACCESS  not-accessible
    STATUS      current
    DESCRIPTION
        "Entry index - this field indicates type of configured map"
    ::= { eltQosMappingCfgEntry 1 }

eltQosMappingCfgEnable OBJECT-TYPE
    SYNTAX      TruthValue
    MAX-ACCESS  read-write
    STATUS      current
    DESCRIPTION
       "This field indicates if mapping is enabled."
    DEFVAL { false }
    ::= { eltQosMappingCfgEntry 2 }

--------------------------------------------------------------------------------
-- eltQosTrafficLimiterMode
--------------------------------------------------------------------------------

eltQosTrafficLimiterMode OBJECT-TYPE
    SYNTAX      EltQosTrafficLimiterMode
    MAX-ACCESS  read-write
    STATUS      current
    DESCRIPTION
        "The scalar indicates in which units of measurement
         the traffic speed and bucket size will be measured in
         storm-control and rate-limit."
    DEFVAL { kbps }
    ::= { eltMesQosCliMib 14 }

--------------------------------------------------------------------------------
-- eltQosPolicerConfigTable
--------------------------------------------------------------------------------

eltQosPolicerConfigTable OBJECT-TYPE
    SYNTAX      SEQUENCE OF EltQosPolicerConfigEntry
    MAX-ACCESS  not-accessible
    STATUS      current
    DESCRIPTION
        "This table specifies additional the policers to rlQosPolicerTable."
    ::= { eltMesQosCliMib 15 }

eltQosPolicerConfigEntry OBJECT-TYPE
    SYNTAX      EltQosPolicerConfigEntry
    MAX-ACCESS  not-accessible
    STATUS      current
    DESCRIPTION
        "This entry specifies additional the policers to rlQosPolicerTable."
    AUGMENTS { rlQosPolicerEntry }
    ::= { eltQosPolicerConfigTable 1 }

EltQosPolicerConfigEntry ::= SEQUENCE {
    eltQosPolicerConfigCirPps         Unsigned32,
    eltQosPolicerConfigCbsPakets      Unsigned32,
    eltQosPolicerConfigPpsAction      EltPolicerAction,
    eltQosPolicerConfigPirPps         Unsigned32,
    eltQosPolicerConfigPbsPakets      Unsigned32,
    eltQosPolicerConfigPpsPeakAction  EltPolicerAction
}

eltQosPolicerConfigCirPps OBJECT-TYPE
    SYNTAX      Unsigned32
    MAX-ACCESS  read-write
    STATUS      current
    DESCRIPTION
        "Committed rate value in packets per second.
         Rate equal to 0 means that the rate limit does not apply
         to traffic."
    DEFVAL { 0 }
    ::= { eltQosPolicerConfigEntry 1 }

eltQosPolicerConfigCbsPakets OBJECT-TYPE
    SYNTAX      Unsigned32
    MAX-ACCESS  read-write
    STATUS      current
    DESCRIPTION
        "Committed burst in packets."
    DEFVAL { 0 }
    ::= { eltQosPolicerConfigEntry 2 }

eltQosPolicerConfigPpsAction OBJECT-TYPE
    SYNTAX      EltPolicerAction
    MAX-ACCESS  read-write
    STATUS      current
    DESCRIPTION
        "Out of profile in pps Action."
    ::= { eltQosPolicerConfigEntry 3 }

eltQosPolicerConfigPirPps OBJECT-TYPE
    SYNTAX      Unsigned32
    MAX-ACCESS  read-write
    STATUS      current
    DESCRIPTION
        "Peak rate value in packets per second.
         When both this and eltQosPolicerConfigPbsPakets
         are 0 this means the mode is Single Rate and 
         when they are both non 0 this means the mode is
         Two Rate."
    DEFVAL { 0 }
    ::= { eltQosPolicerConfigEntry 4 }

eltQosPolicerConfigPbsPakets OBJECT-TYPE
    SYNTAX      Unsigned32
    MAX-ACCESS  read-write
    STATUS      current
    DESCRIPTION
        "Peak burst value in packets.
         When both this and eltQosPolicerConfigPirPps are
         0 this means the mode is Single Rate and when 
         they are both non 0 this means the mode is Two Rate."
    DEFVAL { 0 }
    ::= { eltQosPolicerConfigEntry 5 }

eltQosPolicerConfigPpsPeakAction OBJECT-TYPE
    SYNTAX      EltPolicerAction
    MAX-ACCESS  read-write
    STATUS      current
    DESCRIPTION
        "Out of profile in pps peak action."
    ::= { eltQosPolicerConfigEntry 6 }

END
