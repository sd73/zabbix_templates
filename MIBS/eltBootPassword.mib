ELTEX-MES-BOOTPASSWORD DEFINITIONS ::= BEGIN

-- Title:                ELTEX MES-Series Switches
-- Version:              1.0
-- Date:                 14-Dec-2012

IMPORTS
    MODULE-IDENTITY, OBJECT-TYPE                FROM SNMPv2-SMI
    TruthValue, RowStatus, DisplayString,
    DateAndTime, TEXTUAL-CONVENTION             FROM SNMPv2-TC
    eltMesDevParams                             FROM ELT-MES-DEV-PARAMS;

eltMesBootPassword MODULE-IDENTITY
    LAST-UPDATED "201212140000Z"
    ORGANIZATION "Eltex Enterprise Co, Ltd."
    CONTACT-INFO
          "www.eltex.nsk.ru"
    DESCRIPTION
          "This private MIB module defines Eltex's private MIBs."
    REVISION "201212140000Z"
    DESCRIPTION
          "Initial revision."
    ::= { eltMesDevParams 17 }

eltBootPasswordString OBJECT-TYPE
    SYNTAX        OCTET STRING (SIZE(0..16))
    MAX-ACCESS    read-write
    STATUS        current
    DESCRIPTION   "Specifies boot-menu password string."
    ::= { eltMesBootPassword 1 }

END
