ELTEX-DYING-GASP-MIB DEFINITIONS ::= BEGIN

-- Title:      Eltex Dying Gasp Configuration
-- Version:    1.1
-- Date:       10 Jul 2017

IMPORTS
    OBJECT-TYPE                FROM SNMPv2-SMI
    TruthValue                 FROM SNMPv2-TC
    rndErrorSeverity,
    rndErrorDesc               FROM RADLAN-DEVICEPARAMS-MIB
    eltMesSystemExtMIB         FROM ELTEX-MES-MNG-MIB;

eltMesDyingGasp MODULE-IDENTITY
                LAST-UPDATED "201707100000Z"
                ORGANIZATION "Eltex Enterprise Co, Ltd."
                CONTACT-INFO "www.eltex.nsk.ru"
                DESCRIPTION "The MIB module for managing dying gasp handling event."

                REVISION "201707100000Z"
                DESCRIPTION "Add DEFVAL for all objects."

                REVISION "201610110000Z"
                DESCRIPTION "Initial revision."
        ::= { eltMesSystemExtMIB 1 }
        
EltDyingGaspNotificationType ::= TEXTUAL-CONVENTION
        STATUS      current
        DESCRIPTION "The type of event that notifies about dying gasp."
        SYNTAX INTEGER  {
                            syslog(1),
                            snmp-trap(2),
                            oam-pdu(3)
                        }

eltMesDyingGaspNotifs  OBJECT IDENTIFIER ::= { eltMesDyingGasp 0 }
eltMesDyingGaspObjects OBJECT IDENTIFIER ::= { eltMesDyingGasp 1 }

eltDyingGaspAdminReloadEnable OBJECT-TYPE
    SYNTAX      TruthValue
    MAX-ACCESS  read-write
    STATUS      current
    DEFVAL      { true }
    DESCRIPTION
        "Indicates whether the reboot message is enabled or not."
    ::= { eltMesDyingGaspObjects 4 }

eltDyingGaspAdminReloadTrap NOTIFICATION-TYPE
    OBJECTS   {rndErrorDesc, rndErrorSeverity }
    STATUS current
    DESCRIPTION
        "When the reload requested administratively, a trap will be generated."
    ::= { eltMesDyingGaspNotifs 2 }
    
eltDyingGaspEnable OBJECT-TYPE
    SYNTAX      TruthValue
    MAX-ACCESS  read-write
    STATUS      current
    DEFVAL      { true }
    DESCRIPTION
        "Indicates whether the dying gasp handler is enabled or not."
    ::= { eltMesDyingGaspObjects 1 }

eltDyingGaspPrimaryNotification OBJECT-TYPE
    SYNTAX      EltDyingGaspNotificationType
    MAX-ACCESS  read-write
    STATUS      current
    DEFVAL      { oam-pdu }
    DESCRIPTION
        "The first event that occurs, when dying gasp is detected."
    ::= { eltMesDyingGaspObjects 2 }

eltDyingGaspSecondaryNotification OBJECT-TYPE
    SYNTAX      EltDyingGaspNotificationType
    MAX-ACCESS  read-write
    STATUS      current
    DEFVAL      { snmp-trap }
    DESCRIPTION
        "The second event that occurs, when dying gasp is detected."
    ::= { eltMesDyingGaspObjects 3 }

eltDyingGaspTrap NOTIFICATION-TYPE
    OBJECTS   { rndErrorSeverity }
    STATUS current
    DESCRIPTION
        "When the dying gasp occurs, a trap will be generated."
    ::= { eltMesDyingGaspNotifs 1 }

END
