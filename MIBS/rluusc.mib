RADLAN-UUSC-MIB DEFINITIONS ::= BEGIN

-- Title:               RADLAN LOCALIZATION ROS
--                      This Private MIB supports the unknown
--                                                unicast storm control on Vlaue Blade
-- Version:             7.45
-- Date:                04 July 2007

IMPORTS
    rnd                                 FROM RADLAN-MIB
    OBJECT-TYPE                         FROM RFC-1212
    Counter                             FROM RFC1155-SMI
    PhysAddress                         FROM RFC1213-MIB;

    rlUnknowUnicastStormCtrlFastEthernet MODULE-IDENTITY
         LAST-UPDATED "200707040000Z"
         ORGANIZATION "Marvell Semiconductor, Inc."
         CONTACT-INFO 
			"5488 Marvell Lane
			Santa Clara, CA 95054
			USA

			Website:  www.marvell.com"
         DESCRIPTION "The private MIB module definition for
                unknown unicast storm control on Diamond Opal."
         REVISION "200707040000Z"
         DESCRIPTION "Initial revision."
        ::= { rnd 125 }

rlUnknowUnicastStormCtrlFastEthernetRate OBJECT-TYPE
       SYNTAX INTEGER
       ACCESS                read-write
       STATUS                      mandatory
       DESCRIPTION "The rate configured for Unknown unicast storm control"
       ::= { rlUnknowUnicastStormCtrlFastEthernet 1}

rlUnknowUnicastStormCtrlFastEthernetStatus OBJECT-TYPE
        SYNTAX  INTEGER { enabled(1), disabled(2) }
        ACCESS         read-write
        STATUS                 mandatory
        DESCRIPTION "Enable/Disable unknown unicast storm control"
        ::= { rlUnknowUnicastStormCtrlFastEthernet 2}


END
